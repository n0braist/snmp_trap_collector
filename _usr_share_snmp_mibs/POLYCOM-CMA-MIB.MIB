POLYCOM-CMA-MIB DEFINITIONS ::= BEGIN

IMPORTS
--  TRAP-TYPE                FROM RFC-1215
  DateAndTime, TruthValue, TEXTUAL-CONVENTION FROM SNMPv2-TC
  MODULE-IDENTITY, OBJECT-TYPE, NOTIFICATION-TYPE, enterprises, Counter32,
  Integer32,Counter64 FROM SNMPv2-SMI
  ItuPerceivedSeverity FROM ITU-ALARM-TC-MIB
  InetAddressType, InetAddress, InetPortNumber FROM INET-ADDRESS-MIB
  OBJECT-GROUP, NOTIFICATION-GROUP FROM SNMPv2-CONF;

polycom MODULE-IDENTITY
  LAST-UPDATED  "201407240000Z"
  ORGANIZATION  "Polycom Inc."
  CONTACT-INFO  "Thomas Filarecki"
  DESCRIPTION "This is the Converged Media Application (CMA) MIB."
  DESCRIPTION "Updated descriptions"
  REVISION      "201407240000Z"
  DESCRIPTION "Initial draft"
  ::= { enterprises 13885 }

-------------------------------------------------------------------------------
-- Object Identifiers
-------------------------------------------------------------------------------
    
cma                                OBJECT IDENTIFIER ::= { polycom 14 }
cmaConfigObjects                   OBJECT IDENTIFIER ::= { cma 100 }
cmaStatusObjects                   OBJECT IDENTIFIER ::= { cma 200 }
cmaAlertObjects                    OBJECT IDENTIFIER ::= { cma 300 }

cmaAlertObjectsGeneral             OBJECT IDENTIFIER ::= { cmaAlertObjects 10 }
cmaAlertObjectsAlerts              OBJECT IDENTIFIER ::= { cmaAlertObjects 20 }

-----------------------------------------------------------------------------------
-- CMA configuration data
-----------------------------------------------------------------------------------

cmaConfigGeneral                   OBJECT IDENTIFIER ::= { cmaConfigObjects 10 }
cmaConfigContact                   OBJECT IDENTIFIER ::= { cmaConfigObjects 20 }
cmaConfigNetwork                   OBJECT IDENTIFIER ::= { cmaConfigObjects 30 }
cmaConfigLog                       OBJECT IDENTIFIER ::= { cmaConfigObjects 40 }
-- cmaConfigDatabase                  OBJECT IDENTIFIER ::= { cmaConfigObjects 50 }
cmaConfigLDAP                      OBJECT IDENTIFIER ::= { cmaConfigObjects 60 }
cmaConfigTime                      OBJECT IDENTIFIER ::= { cmaConfigObjects 70 }
cmaConfigRedundancy                OBJECT IDENTIFIER ::= { cmaConfigObjects 80 }
cmaConfigRemoteAlert               OBJECT IDENTIFIER ::= { cmaConfigObjects 90 }
cmaConfigEmail                     OBJECT IDENTIFIER ::= { cmaConfigObjects 110 }

cmaConfigUI                        OBJECT IDENTIFIER ::= { cmaConfigObjects 120 }
cmaConfigEndpoint                  OBJECT IDENTIFIER ::= { cmaConfigObjects 130 }

cmaConfigSite                      OBJECT IDENTIFIER ::= { cmaConfigObjects 140 }
cmaConfigSiteTopology              OBJECT IDENTIFIER ::= { cmaConfigSite 1 }
cmaConfigSiteProvisioning          OBJECT IDENTIFIER ::= { cmaConfigSite 2 }

cmaConfigConference                OBJECT IDENTIFIER ::= { cmaConfigObjects 150 }
cmaConfigConferenceGeneral         OBJECT IDENTIFIER ::= { cmaConfigConference 1 }

cmaConfigRooms                     OBJECT IDENTIFIER ::= { cmaConfigObjects 160 }

cmaConfigSnmp                      OBJECT IDENTIFIER ::= { cmaConfigObjects 180 }
cmaConfigLicenses                  OBJECT IDENTIFIER ::= { cmaConfigObjects 190 }
cmaEmailCustomization              OBJECT IDENTIFIER ::= { cmaConfigObjects 200 }
cmaConfigCDRArchive                OBJECT IDENTIFIER ::= { cmaConfigObjects 210 }

--cmaConfigProvisioningProfiles      OBJECT IDENTIFIER ::= { cmaConfigObjects 240 }
--cmaConfigCalendaring               OBJECT IDENTIFIER ::= { cmaConfigObjects 250 } 

cmaConfigLocalUserAccount          OBJECT IDENTIFIER ::= { cmaConfigObjects 220 }       
cmaConfigLocalPasswordRequirement  OBJECT IDENTIFIER ::= { cmaConfigObjects 230 }

-----------------------------------------------------------------------------------
-- CMA Status data
-----------------------------------------------------------------------------------

cmaStatusUsers                     OBJECT IDENTIFIER ::= { cmaStatusObjects 10 }  -- connected users
cmaStatusLicenses                  OBJECT IDENTIFIER ::= { cmaStatusObjects 30 } 
cmaStatusEndpointManagement        OBJECT IDENTIFIER ::= { cmaStatusObjects 50 } 

cmaStatusDevice                    OBJECT IDENTIFIER ::= { cmaStatusObjects 60 } 
cmaStatusDeviceMCU                 OBJECT IDENTIFIER ::= { cmaStatusDevice 1 } 
cmaStatusDeviceEndpoint            OBJECT IDENTIFIER ::= { cmaStatusDevice 2 } 
cmaStatusDeviceVBP                 OBJECT IDENTIFIER ::= { cmaStatusDevice 3 } 
cmaStatusDeviceDMA                 OBJECT IDENTIFIER ::= { cmaStatusDevice 4 } 
cmaStatusDevicePeripherals         OBJECT IDENTIFIER ::= { cmaStatusDevice 5 } 
cmaStatusDeviceRPAD                 OBJECT IDENTIFIER ::= { cmaStatusDevice 6 } 
cmaStatusDeviceSBC                 OBJECT IDENTIFIER ::= { cmaStatusDevice 7 } 

cmaStatusConferenceSummary         OBJECT IDENTIFIER ::= { cmaStatusObjects 70 } 
cmaStatusConferencesOngoing        OBJECT IDENTIFIER ::= { cmaStatusObjects 80 } 
cmaStatusAlerts                    OBJECT IDENTIFIER ::= { cmaStatusObjects 90 } 
cmaStatusRedundancy                OBJECT IDENTIFIER ::= { cmaStatusObjects 100 } 
cmaStatusSites                     OBJECT IDENTIFIER ::= { cmaStatusObjects 110 } 
cmaStatusSiteLinks                 OBJECT IDENTIFIER ::= { cmaStatusObjects 120 }
cmaStatusSubnets                   OBJECT IDENTIFIER ::= { cmaStatusObjects 130 }

-----------------------------------------------------------------------------------
-- SMIv2 Conformance groups
-----------------------------------------------------------------------------------

cmaConformance                     OBJECT IDENTIFIER ::= { cma 1000 }
cmaConfigConformance               OBJECT IDENTIFIER ::= { cmaConformance 10 }
cmaStatusConformance               OBJECT IDENTIFIER ::= { cmaConformance 20 }
cmaNotificationConformance         OBJECT IDENTIFIER ::= { cmaConformance 30 }

-------------------------------------------------------------------------------
-- Textual Conventions
-------------------------------------------------------------------------------

--NetworkAddress ::= SEQUENCE
--{
--   addressType                InetAddressType,
--   address            InetAddress
--}

CmaDefaultTableIndexRange  ::= TEXTUAL-CONVENTION
   DISPLAY-HINT  "d"
   STATUS        current
   DESCRIPTION   "Default table index range."
   SYNTAX        Integer32 (1..2147483647) 

CmaTimeZone      ::= TEXTUAL-CONVENTION
   DISPLAY-HINT  "1a1d:1d"
   STATUS        current
   DESCRIPTION   "A time zone specification.
                  field     octets    contents             range
                  -----     ------    --------             -----
                    1          1      direction from UTC   '+' / '-'
                    2          2      hours from UTC       0..13
                    3          3      minutes from UTC     0..59
                
                  Note:
                  - Daylight saving time in New Zealand is +13."
   SYNTAX         OCTET STRING (SIZE(3))

CmaConfigSystemLogLevel  ::= TEXTUAL-CONVENTION
   STATUS        current
   DESCRIPTION   "CMA System log level values."
   SYNTAX        INTEGER { debug(0), info(1), warn(2), error(3), fatal(4), off(5) }

CmaConfigLdapSecurityLevel  ::= TEXTUAL-CONVENTION
   STATUS        current
   DESCRIPTION   "CMA LDAP security level values."
   SYNTAX        INTEGER
                 {
                    plain(1),
                    startTLS(2),
                    ldaps(3)
                 }

-- CmaConfigDatabaseType  ::= TEXTUAL-CONVENTION
--    STATUS        current
--    DESCRIPTION   "CMA database type values."
--    SYNTAX        INTEGER
--                  {
--                     internal(1)
--                  }

CmaConfigSystemTimeSourceType  ::= TEXTUAL-CONVENTION
   STATUS        current
   DESCRIPTION   "CMA time source values."
   SYNTAX        INTEGER
                 {
                    internal(1),
                    external(2)
                 }

CmaConfigRemoteAlertLevel  ::= TEXTUAL-CONVENTION
   STATUS        current
   DESCRIPTION   "CMA remote alert level values."
   SYNTAX        INTEGER
                 {
                    none(0),
                    info(1),
                    minor(2),
                    major(4)
                 }

-- CmaConfigGatekeeperMessageType  ::= TEXTUAL-CONVENTION
--    STATUS        current
--    DESCRIPTION   "CMA gatekeeper message type values."
--    SYNTAX        INTEGER
--                  {
--                     rrq(0),                              ---- Registration Request
--                     grq(1),                              ---- Gatekeeper Request
--                     irrIrq(2),                           ---- Information Reponse/Information Request
--                     lwrrq(3),                            ---- Light-weight Registration Request
--                     urq(4),                              ---- Unregistration Request
--                     lrq(5),                              ---- Location Request
--                     arq(6),                              ---- Admission Request
--                     drq(7),                              ---- Disengage Request
--                     brq(8),                              ---- Bandwidth Request
--                     setup(9),                            ---- Setup message
--                     releaseComplete(10),         
--                     nsm(11),                             ---- Non-standard message
--                     other(12)                            ---- other call state changed
--                  }

CmaPrimaryGatekeeperEndpointRegistrationType  ::= TEXTUAL-CONVENTION
   STATUS        current
   DESCRIPTION   "CMA gatekeeper endpoint registration type values."
   SYNTAX        INTEGER
                 {
                    all(1),
                    predefinedOnly(2),
                    inDefineSites(3),
                    predefinedPrefixesOnly(4)    
                 }

CmaGatekeeperCallModel  ::= TEXTUAL-CONVENTION
   STATUS        current
   DESCRIPTION   "CMA gatekeeper call model values."
   SYNTAX        INTEGER
                 {
                    directMode(1),
                    routedMode(2)
                 }

CmaMcuType  ::= TEXTUAL-CONVENTION
   STATUS        current
   DESCRIPTION   "CMA MCU type values."
   SYNTAX        INTEGER
                 {
                    other(0),
                    rmx(1),
                    mgc(2),
                    mrc(3)
                 }

CmaDeviceStatus  ::= TEXTUAL-CONVENTION
   STATUS        current
   DESCRIPTION   "CMA device status values."
   SYNTAX        INTEGER
                 {
                    online(1),
                    offline(2)
                 }

CmaPeripheralPairingStatus ::= TEXTUAL-CONVENTION
   STATUS        current
   DESCRIPTION   "CMA device peripheral status values."
   SYNTAX        INTEGER
                 {
                    notPaired(0),
                    connected(1),
                    disconnected(2),
                    unknown(3)
                 }

CmaPeripheralIconState ::= TEXTUAL-CONVENTION
   STATUS        current
   DESCRIPTION   "CMA peripheral icon status values."
   SYNTAX        INTEGER
                 {
                    noPeripherals(0),
                    hasPeripherals(1),
                    hasPeripheralsWithErrors(2)
                 }


CmaPeripheralAlertState ::= TEXTUAL-CONVENTION
   STATUS        current
   DESCRIPTION   "CMA peripheral alert status values."
   SYNTAX        INTEGER
                 {
                    noAlert(0),
                    venusSwIncompatible(1)
                 }

CmaEndpointType  ::= TEXTUAL-CONVENTION
   STATUS        current
   DESCRIPTION   "CMA endpoint type values."
   SYNTAX        INTEGER
                 {
                    other(0),
                    vseries(1),
                    vtx1000(6),
                    tandberg(7),
                    hdx(8),
                    cmad(9),
                    qdx(10),
                    vvx(11), 
                    lifesize(12), 
                    venus(13),
                    rabbiteye(14),
                    rpmobile(15),
		    		groupseries(16),
		    		rpdesktop(17)
                 }

CmaDeviceRegistrationStatus  ::= TEXTUAL-CONVENTION
   STATUS        current
   DESCRIPTION   "CMA device registration status values."
   SYNTAX        INTEGER
                 {
                    unknown(0),
                    registered(1),
                    notRegistered(2),
                    registering(3),
                    rejected(4),
                    notApplicable(5)  
                 }

CmaDeviceManagementStatus   ::= TEXTUAL-CONVENTION
   STATUS        current
   DESCRIPTION   "CMA endpoint management status values."
   SYNTAX        INTEGER
                 {
                    unknown(0),
                    ok(1),
                    notApplicable(2),
                    notResponding(3),
                    heartbeatTimeout(4),
                    signedOut(5),
                    credentialsRequired(6),
                    credentialsFailed(7),
                    behindFirewall(8),
                    httpForbidden(9),
                    rebooting(10)
                 }

CmaVbpModel  ::= TEXTUAL-CONVENTION
   STATUS        current
   DESCRIPTION   "CMA VBP model values."
   SYNTAX        INTEGER
                 {
                   unknown(0),
                   stSeries(1)
                 }

CmaConferenceType  ::= TEXTUAL-CONVENTION
   STATUS        current
   DESCRIPTION   "CMA conference type values."
   SYNTAX        INTEGER
                 {
                    audioOnly(1),
                    video(2)
                 }

CmaConferenceStatus  ::= TEXTUAL-CONVENTION
   STATUS        current
   DESCRIPTION   "CMA conference status values."
   SYNTAX        INTEGER
                 {
                    unknown(0),
                    active(1),
                    activeAlerts(2),
                    future(3),         -- for completeness
                    futureAlerts(4),
                    finished(5),       -- for completeness
                    deleted(6),        -- for completeness
                    declined(7)
                 }

CmaSystemAlertType  ::= TEXTUAL-CONVENTION
   STATUS        current
   DESCRIPTION   "CMA system alert values."
   SYNTAX        INTEGER
                 {
                    unknown(0),
                    mcuDown(1),
                    databaseConnectionDown(2),
                    ldapConnectionDown(3),
                    cmaFailOver(4),
                    licenseCloseToMax(5),
                    monitorServiceStopped(7),
                    redundantServerOffline(8),
                    redundancyConflict(9),
                    ldapSysAccountPasswordFailure(10),
                    cdrArchiveFail(12),
                    versionCausedForceToInternal(13),
                    bandwidthUsedSite(14),
                    bandwidthUsedSubnet(15),
                    bandwidthUsedSiteLink(16),
                    auditUsageThresholdExceeded(17),
                    alertDiskSpaceUsageExceeded(18),
                    certificateExirationWarning(19),
                    certificateExpiredWarning(20), 
                    idsPortScanDetected(21),
                    idsDosDetected(22),
                    idsFloodDetected(23),
                    avVirusFound(24),
                    avScanError(25),
                    databaseBackupFailed(26),
                    concurrentCallsThresholdExceeded(27),
                    concurrentCallsExceeded(28),
                    redundancyLicensesExceeded(29),
                    cpuUsageExceeded(30),
                    memoryUsageExceeded(31),
                    licenseExpiration(32),
                    redundancyServerResourceStopped(33),
                    dmaDown(34),
                    incompatibleBundle4EP(35),
                    e164AliasAssignmentFailed(36),
                    systemNamingFailed(37),
                    systemPasswordExpiring(38),
                    systemPasswordExpired(39),
                    provisioningCloseToMax(40),
                    h323IDAssignmentFailed(41),
                    sipURIAssignmentFailed(42),
                    autoSystemBackupFTPFailed(43),
                    remoteSystemLogServerDown(44),
                    remoteCDRServerDown(45)
                 }

CmaEndpointAlertType  ::= TEXTUAL-CONVENTION
   STATUS        current
   DESCRIPTION   "CMA endpoint alert values."
   SYNTAX        INTEGER
                 {
                    remoteControlBatteryLow(0),
                    credentialsRequired(1),
                    credentialsFailed(2),
                    httpForbidden(3),
                    notResponding(4),
                    heartbeatTimeout(5),
                    gatekeeperStatusUnknown(6),
                    gatekeeperRejected(7),
                    gatekeeperUnregistered(8),
                    directoryStatusUnknown(9),
                    directoryNotRegistered(10),
                    presenceStatusUnknown(11),
                    presenceUnregistered(12),
                    helpRequest(13),
                    mgmtUrlNotSet(14),
                    venusDisconnected(15),
                    venusSoftwareIncompatible(16),
                    sipUriNotProvided(17),
                    sipStatusUnknown(18),
                    sipUnregistered(19)
                 }

CmaRedundantServerRole  ::= TEXTUAL-CONVENTION
   STATUS        current
   DESCRIPTION   "CMA redundant server role values."
   SYNTAX        INTEGER
                 {
                    primary(1),
                    alternate(2)
                 }

CmaRedundantServerStatus  ::= TEXTUAL-CONVENTION
   STATUS        current
   DESCRIPTION   "CMA redundant server status values."
   SYNTAX        INTEGER
                 {
                    online(1),
                    offline(2)
                 }

SimplifiedDialingEndpointBitRates   ::= TEXTUAL-CONVENTION
   STATUS        current
   DESCRIPTION   "CMA dial plan service simplified dialing bit rates."
   SYNTAX        INTEGER
                 {
                    notConfigured(0),
                    br1B(1),    -- 1B
                    br2B(2),    -- 2B
                    br3B(3),    -- 3B
                    br4B(4),    -- 4B
                    br5B(5),    -- 5B
                    br6B(6),    -- 6B
                    br64(7),    -- 64 kbps
                    br128(8),   -- 128 kbps
                    br192(9),   -- 192 kbps
                    br256(10),  -- 256 kbps
                    br320(11),  -- 320 kbps
                    br384(12),  -- 384 kbps
                    br448(13),  -- 448 kbps
                    br512(14),  -- 512 kbps
                    br576(15),  -- 576 kbps
                    br640(16),  -- 640 kbps
                    br704(17),  -- 704 kbps
                    br768(18),  -- 768 kbps
                    br1152(19), -- 1152 kbps
                    br1472(20), -- 1472 kbps
                    br1536(21), -- 1536 kbps
                    br1920(22)  -- 1920 kbps
                 }

MgcVideoSessionType    ::=  TEXTUAL-CONVENTION
   STATUS        current
   DESCRIPTION   "MGC video session type."
   SYNTAX        INTEGER
                 {
                    continuousPresence(1),
                    switching(2),
                    transcoding(3)
                  }

ConfOnDemandMgcBitRateType  ::= TEXTUAL-CONVENTION
   STATUS        current
   DESCRIPTION   "MGC bit rate."
   SYNTAX        INTEGER
                 {
                    notConfigured(0),
                    br128(1),   -- 128 kbps
                    br256(2),  -- 256 kbps
                    br384(3),  -- 384 kbps
                    br448(4),  -- 448 kbps
                    br512(5),  -- 512 kbps
                    br576(6),  -- 576 kbps
                    br640(7),  -- 640 kbps
                    br704(8),  -- 704 kbps
                    br768(9),  -- 768 kbps
                    br1152(10), -- 1152 kbps
                    br1472(11), -- 1472 kbps
                    br1536(12), -- 1536 kbps
                    br1920(13)  -- 1920 kbps
                 }

SiteTopoSiteType   ::= TEXTUAL-CONVENTION
   STATUS        current
   DESCRIPTION   "Site type."
   SYNTAX        INTEGER
                 {
                    internetCloud(1), -- Interent
                    networkCloud(2),  -- MPLS/Netowrk Cloud
                    privateSite(3)    -- Private/Site
                 }  

SiteTopoIsdnNumberAssignmentMethodType   ::= TEXTUAL-CONVENTION
   STATUS        current
   DESCRIPTION   "Site topology ISDN number assignment method."
   SYNTAX        INTEGER
                 {
                    none(1),
                    did(2),                -- Direct Inward Dial
                    gwExtensionDialing(3)  -- Gateway + extension 
                 }  

SiteTopoInternetRoutingType    ::= TEXTUAL-CONVENTION
   STATUS        current
   DESCRIPTION   "Site topology internet calling types."
   SYNTAX        INTEGER
                 {
                    notAllowed(1),           -- call routing through internet not allowed
                    viaH323AwareFirewall(2), -- allowed via a H.323 aware firewall
                    viaH323SbcOrAlg(3)       -- allowed via a H.323 aware SBC 
                                             --   (Session Border Control) or ALG
                                             --   (Application level gateway)
                 }

SiteProvisioningDateFormatType    ::= TEXTUAL-CONVENTION
   STATUS        current
   DESCRIPTION   "Site topology provisioning date format."
   SYNTAX        INTEGER
                 {
                    monthDayYear(1),   -- MM-dd-yyy
                    dayMonthYear(2),  -- dd-MM-yyy
                    yearMonthDay(3)   -- yyyy-MM-dd
                 }

SiteProvisioningTimeFormatType   ::= TEXTUAL-CONVENTION
   STATUS        current
   DESCRIPTION   "Site topology provisioning time format."
   SYNTAX        INTEGER
                 {
                    twelveHour(1),
                    twentyFourHour(2)
                 }

SiteNatConfigurationType  ::= TEXTUAL-CONVENTION
   STATUS        current
   DESCRIPTION   "Site topology provisioning NAT configuration type."
   SYNTAX        INTEGER
                 {
                    off(1), 
                    auto(2),
                    manual(3)
                 }

SiteUseGkForMultipointCallsType   ::= TEXTUAL-CONVENTION
   STATUS        current
   DESCRIPTION   "Site topology provisioning use gatekeeper for multipoint calls setting."
   SYNTAX        INTEGER
                 {
                    dynamic(1), 
                    always(2),
                    never(3)
                 }

SiteTimeServerUpdateType   ::=TEXTUAL-CONVENTION
   STATUS        current
   DESCRIPTION   "Time Server would follow time updation in the following ways."  
   SYNTAX        INTEGER
                 {
                    auto(1),
                    manual(2),
                    off(3)      
                 } 
 
SiteQosTypeOfServiceType   ::= TEXTUAL-CONVENTION
   STATUS        current
   DESCRIPTION   "Site topology provisioning QOS type."
   SYNTAX        INTEGER
                 {
                    ipPrecedence(1),
                    diffServ(2)
                 }

SiteQosMtuSizeType     ::= TEXTUAL-CONVENTION
   STATUS        current
   DESCRIPTION   "Site topology provisioning IP call maximum transmission unit values (bytes)"
   SYNTAX        INTEGER
                 {
                    ipCallMtu660(1),   -- 660
                    ipCallMtu780(2),   -- 780
                    ipCallMtu900(3),   -- 900
                    ipCallMtu1020(4),  -- 1020
                    ipCallMtu1140(5),  -- 1140
                    ipCallMtu1280(6),  -- 1280
                    ipCallMtu1500(7)   -- 1500
                 }

SiteQosBandwidthType    ::= TEXTUAL-CONVENTION
   STATUS        current
   DESCRIPTION   "Site topology provisioning IP call maximum line speed values (Kbps)."
   SYNTAX        INTEGER
                 {
                    linespeed64(1),  
                    linespeed128(2),
                    linespeed256(3),
                    linespeed384(4), 
                    linespeed512(5),
                    linespeed768(6),
                    linespeed1024(7),
                    linespeed1472(8),
                    linespeed1920(9),
                    linespeed3840(10),
                    linespeed4096(11), 
                    linespeed6144(12),
                    linespeed8192(13), 
                    linespeed10240(14)
                 }

SiteSecurityEnableEncryptionType  ::= TEXTUAL-CONVENTION
   STATUS        current
   DESCRIPTION   "Site topology provisioning IP call encryption options."
   SYNTAX        INTEGER
                 {
                    off(1),                -- No encryption used
                    whenAvailable(2),      -- encryption used with any enpoint that supports it.
                    requiredForVideo(3),   -- used for all video endpoints in the call, audio & ISDN
                                           --   connection are allowed
                    requiredForAll(4)      -- used for all video endpoints in the call, audio & ISDN
                                           --   connections are not allowed
                 }

SiteSIPTransportProtocolType  ::= TEXTUAL-CONVENTION
   STATUS        current
   DESCRIPTION   "Transport Layer protocol used for SIP."
   SYNTAX        INTEGER
                 {
                    auto(1),   
                    tcp(2),   
                    udp(3),
                    tls(4)
                 }

SiteSIPServerType  ::= TEXTUAL-CONVENTION
   STATUS        current
   DESCRIPTION   "Server used for SIP."
   SYNTAX        INTEGER
                 {
                    standard(1),   
                    polycom(2),   
                    microsoft(3),
                    siemens(4),
                    broadsoft(5),       
                    avaya(6),
                    cisco(7)
                 }

ConferenceTemplateVideoDialType  ::= TEXTUAL-CONVENTION
   STATUS        current
   DESCRIPTION   "Conference template video dial options."
   SYNTAX        INTEGER
                 {
                    dialinOnly(1),    -- dial-in only
                    dialoutOnly(2),   -- dial-out only
                    dialinDialout(3)  -- dial-in and dial-out
                 }

ConferenceTemplateVideoMode    ::= TEXTUAL-CONVENTION
   STATUS        current
   DESCRIPTION   "Conference template video layout modes."
   SYNTAX        INTEGER
                 {
                    videoSwitching(1),
                    oneByOne(2),
                    oneByTwo(3),
                    twoByOne(4),
                    oneByTwoVeritcal(5),
                    oneByTwoHorizontal(6),
                    oneByTwoHorizontalUpper(7),
                    oneAndTwoHorizontal(8),
                    oneAndTwoVertical(9),
                    twoByTwo(10),
                    oneAndThreeHorizontalUpper(11),
                    oneAndThreeHorizontal(12),
                    oneAndThreeVertical(13),
                    oneAndFourHorizontalUpper(14),
                    oneAndFourHorizontal(15),
                    oneAndFourVertical(16),
                    oneAndFive(17),
                    oneAndSeven(18),
                    threeByThree(19),
                    oneAndEightLower(20), 
                    oneAndEightUpper(21),
                    oneAndEightCentral(22),
                    fourByFour(23),
                    twoAndEight(24),
                    oneAndTwelve(25)
                 }

ConferenceTemplateVideoAlgorithm   ::= TEXTUAL-CONVENTION
   STATUS        current
   DESCRIPTION   "Conference template video compression algorithm types."
   SYNTAX        INTEGER
                 {
                    auto(1),
                    h261(2),
                    h263(3),
                    h264(4)
                 }

ConferenceTemplateContentType   ::= TEXTUAL-CONVENTION
   STATUS        current
   DESCRIPTION   "Conference template people and content format types."
   SYNTAX        INTEGER
                 {
                    none(1),
                    peopleAndContent(2),
                    peopleAndContentV0(3),
                    polycomVisualConcertPc(4),
                    polycomVisualConcertFx(5),
                    duoVideo(6) 
                 }

ConferenceTemplateConferenceSpeed  ::=  TEXTUAL-CONVENTION
   STATUS        current
   DESCRIPTION   "Conference template conference speeds (Kbps)."
   SYNTAX        INTEGER
                 {
                    confSpeed128(1),
                    confSpeed256(2),
                    confSpeed320(3),
                    confSpeed384(4),
                    confSpeed512(5),
                    confSpeed768(6),
                    confSpeed1152(7),
                    confSpeed1472(8),
                    confSpeed1536(9),
                    confSpeed1920(10),
                    confSpeed4096(11),
                    confSpeed6144(12),
                    confSpeed8192(13),
                    confSpeed10240(14),
                    confSpeedBridgedAudio(15)
                 }

ConferenceTemplateVideoQualityType  ::= TEXTUAL-CONVENTION
   STATUS        current
   DESCRIPTION   "Conference video quality type."
   SYNTAX        INTEGER
                 {
                    motion(1),
                    sharpness(2)
                 }

ConferenceTemplateT120Rates       ::= TEXTUAL-CONVENTION
   STATUS        current
   DESCRIPTION   "Conference T.120 transfer rate."
   SYNTAX        INTEGER
                 {
                    none(1),        -- T.120 is not enabled
                    mlp6dot4(2),    -- MLP 6.4K
                    mlp14dot4(3),   -- MLP 14.4K
                    mlp16(4),       -- MLP 16K
                    mlp22dot4(5),   -- MLP 22.4K
                    mlp24(6),       -- MLP 24K
                    mlp30dot4(7),   -- MLP 30.4K
                    mlp32(8),       -- MLP 32K
                    mlp38dot4(9),   -- MLP 38.4
                    mlp40(10),      -- MLP 40K
                    mlp46dot4(11),  -- MLP 46.4K
                    hmlp14dot4(12), -- HMLP 14.4K
                    hmlp62dot4(13)  -- HMLP 62.4K
                 }

ConferenceTemplateAudioAlgorithms    ::= TEXTUAL-CONVENTION
   STATUS        current
   DESCRIPTION   "Conference audio compression algorithm used on the MGC MCU."
   SYNTAX        INTEGER
                 {
                    auto(1), 
                    siren7b16(2),
                    siren14b24(3),
                    siren14b32(4),
                    siren14b48(5),
                    g722b56(6),
                    g711b56(7)
                 }
ConferenceTemplateLectureModeType   ::= TEXTUAL-CONVENTION
   STATUS        current
   DESCRIPTION   "Conference template lecture mode values."
   SYNTAX        INTEGER
                 {
                    none(0),
                    lecture(1),       -- Lecture Mode
                    presentation(2)   -- Presentation Mode
                 }

ConferenceTemplateHDResolution   ::= TEXTUAL-CONVENTION
   STATUS        current
   DESCRIPTION   "Conference template high definition resolution values."
   SYNTAX        INTEGER
                 {
                    sd(1),
                    hd720p30(2),
                    hd720p60(3),
                    hd1080(4)
                 }

ConferenceTemplateLastQuitType   ::= TEXTUAL-CONVENTION
   STATUS        current
   DESCRIPTION   "Conference template auto terminate quit type."
   SYNTAX        INTEGER
                 {
                    afterLastQuit(1),
                    whenLastRemain(2)
                 }

ConferenceTemplateTelepresenceMode   ::= TEXTUAL-CONVENTION
   STATUS        current
   DESCRIPTION   "Conference template telepresence mode."
   SYNTAX        INTEGER
                 {
                    auto(1),
                    on(2),
                    off(3)
                 }

ConferenceTemplateTelepresenceLayoutMode   ::= TEXTUAL-CONVENTION
   STATUS        current
   DESCRIPTION   "Conference template telepresence layout mode."
   SYNTAX        INTEGER
                 {
                    manual(1),
                    cp(2),
                    roomSwitch(3)
                 }

ConferenceTemplateMaxResolution   ::= TEXTUAL-CONVENTION
   STATUS        current
   DESCRIPTION   "Conference template maximum resolution."
   SYNTAX        INTEGER
                 {
                                        auto(1),
                                        cif(2),
                                        sd(3),
                                        hd720(4),
                                        hd1080(5)
                 }

ConferenceTemplateContentMode   ::= TEXTUAL-CONVENTION
   STATUS        current
   DESCRIPTION   "Conference template content mode."
   SYNTAX        INTEGER
                 {
                                        graphics(1),
                                        hiResGraphics(2),
                                        liveVideo(3)
                 }

ConferenceTemplateContentProtocol   ::= TEXTUAL-CONVENTION
   STATUS        current
   DESCRIPTION   "Conference template content protocol."
   SYNTAX        INTEGER
                 {
                                        h263(1),
                                        upToH264(2)
                 }

ConferenceTemplateDisplayLanguage   ::= TEXTUAL-CONVENTION
   STATUS        current
   DESCRIPTION   "Conference template gathering display language."
   SYNTAX        INTEGER
                 {
                                        english(1),
                                        german(2),
                                        spanishSouthAmerica(3),
                                        french(4),
                                        japanese(5),
                                        korean(6),
                                        chineseSimplified(7)
                 }

ConferenceTemplateRecordingPolicy   ::= TEXTUAL-CONVENTION
   STATUS        current
   DESCRIPTION   "Conference template recording policy."
   SYNTAX        INTEGER
                 {
                                        immediately(1),
                                        uponRequest(2)
                 }

ConferenceTemplateSkin   ::= TEXTUAL-CONVENTION
   STATUS        current
   DESCRIPTION   "Conference template skin."
   SYNTAX        INTEGER
                 {
                                        cleanSlate(1),
                                        simplyBlue(2),
                                        sapphireJewel(3),
                                        loopy(4)
                 }
                                       
UserRoleSchedulingLevel   ::= TEXTUAL-CONVENTION
   STATUS        current
   DESCRIPTION   "User role scheduling levels."
   SYNTAX        INTEGER
                 {
                    basic(1), 
                    advanced(2),
                    view-only(3)
                 }

UserGroupType    ::= TEXTUAL-CONVENTION
   STATUS        current
   DESCRIPTION   "User group type."
   SYNTAX        INTEGER
                 {
                    local(1), 
                    enterprise(2)
                 }

RedundancyStatusType    ::= TEXTUAL-CONVENTION
   STATUS        current
   DESCRIPTION   "CMA redundancy status."
   SYNTAX        INTEGER
                 {
                    notConfigured(1), 
                    configured(2),           -- configured and okay
                    errorNeedsVirtualIp(3),  -- needs virtual IP
                    errorSecondaryDown(4)    -- secondary CMA server is down
                 }
SnmpVersionType   ::= TEXTUAL-CONVENTION
   STATUS        current
   DESCRIPTION   "CMA SNMP version."
   SYNTAX        INTEGER
                 {
                    disabled(1), 
                    v2c(2),     
                    v3Usm(3)     -- V3 User Based Security Model
                 }

SnmpTransportType     ::= TEXTUAL-CONVENTION
   STATUS        current
   DESCRIPTION   "CMA SNMP transport type."
   SYNTAX        INTEGER
                 {
                    tcp(1), 
                    udp(2)
                 }

SnmpAuthenticationType     ::= TEXTUAL-CONVENTION
   STATUS        current
   DESCRIPTION   "CMA SNMP authentication type."
   SYNTAX        INTEGER
                 {
                    sha(1), 
                    md5(2),
                    none(3)
                 } 
SnmpEncryptionType      ::= TEXTUAL-CONVENTION
   STATUS        current
   DESCRIPTION   "CMA SNMP encryption type."
   SYNTAX        INTEGER
                 {
                    des(1), 
                    aes128bit(2),
                    none(3)
                 } 

SnmpNotificationType        ::= TEXTUAL-CONVENTION
   STATUS        current
   DESCRIPTION   "CMA SNMP notification type."
   SYNTAX        INTEGER
                 {
                    trap(1), 
                    inform(2)
                 } 

CmaConfigDayOfWeek      ::= TEXTUAL-CONVENTION
   STATUS        current
   DESCRIPTION   ""
   SYNTAX        INTEGER
                 {
                    undefined(0),       
                    sunday(1),  
                    monday(2),
                    tuesday(3),
                    wednesday(4),
                    thursday(5),
                    friday(6),
                    saturday(7)
                 }

-------------------------------------------------------------------------------
-- Configuration Group
-------------------------------------------------------------------------------

-- START general configuration

cmaConfigGeneralGroup  OBJECT-GROUP
   OBJECTS
   {
      cmaConfigSoftwareVersion,
      cmaConfigCMADSoftwareVersion,
      cmaConfigRemoteAccessEnabled,
      cmaConfigCMADMacSoftwareVersion,
      cmaConfigCMADShippedSoftwareVersion,
      cmaConfigCMADMacShippedSoftwareVersion,
      cmaConfigHardwareVersion
   }
   STATUS current
   DESCRIPTION "CMA general configuration group."
   ::= { cmaConfigConformance 1 }

cmaConfigSoftwareVersion   OBJECT-TYPE
   SYNTAX            OCTET STRING (SIZE(1..255))
   MAX-ACCESS        read-only
   STATUS            current
   DESCRIPTION "CMA software version."
   ::= { cmaConfigGeneral 1 }

cmaConfigCMADSoftwareVersion   OBJECT-TYPE
   SYNTAX            OCTET STRING (SIZE(1..255))
   MAX-ACCESS        read-only
   STATUS            current
   DESCRIPTION "Software version of the downloadable CMADesktop client."
   ::= { cmaConfigGeneral 2 }

cmaConfigRemoteAccessEnabled  OBJECT-TYPE        
   SYNTAX            TruthValue         
   MAX-ACCESS        read-only          
   STATUS            current    
   DESCRIPTION "Remote access enabled flag"     
   ::= { cmaConfigGeneral 3 }

cmaConfigCMADMacSoftwareVersion   OBJECT-TYPE
   SYNTAX            OCTET STRING (SIZE(1..255))
   MAX-ACCESS        read-only
   STATUS            current
   DESCRIPTION "Software version of the downloadable CMADesktop Mac client."
   ::= { cmaConfigGeneral 4 }
   
cmaConfigCMADShippedSoftwareVersion   OBJECT-TYPE
   SYNTAX            OCTET STRING (SIZE(1..255))
   MAX-ACCESS        read-only
   STATUS            current
   DESCRIPTION "Software version of the shipped CMADesktop client."
   ::= { cmaConfigGeneral 5 }
   
cmaConfigCMADMacShippedSoftwareVersion   OBJECT-TYPE
   SYNTAX            OCTET STRING (SIZE(1..255))
   MAX-ACCESS        read-only
   STATUS            current
   DESCRIPTION "Software version of the shipped CMADesktop Mac client."
   ::= { cmaConfigGeneral 6 }   

cmaConfigHardwareVersion  OBJECT-TYPE
   SYNTAX            OCTET STRING (SIZE(1..255))
   MAX-ACCESS        read-only
   STATUS            current
   DESCRIPTION "CMA Hardware Version."
   ::= { cmaConfigGeneral 7 }

-- END general configuration

-- START Admin contact configuration

cmaConfigContactGroup  OBJECT-GROUP
   OBJECTS
   {
      cmaConfigAdminContactName,
      cmaConfigAdminContactEmailAddress,
      cmaConfigAdminContactTitle,
      cmaConfigAdminContactDepartment,
      cmaConfigAdminContactCity,
      cmaConfigAdminContactPhoneNumber
   }
   STATUS current
   DESCRIPTION "CMA administrator contact configuration group."
   ::= { cmaConfigConformance 2 }

cmaConfigAdminContactName   OBJECT-TYPE
   SYNTAX            OCTET STRING (SIZE(1..255))
   MAX-ACCESS        read-only
   STATUS            current
   DESCRIPTION "CMA administrator contact name."
   ::= { cmaConfigContact 1 }

cmaConfigAdminContactEmailAddress   OBJECT-TYPE
   SYNTAX            OCTET STRING (SIZE(1..255))
   MAX-ACCESS        read-only
   STATUS            current
   DESCRIPTION "CMA administrator email address."
   ::= { cmaConfigContact 2 }

cmaConfigAdminContactTitle   OBJECT-TYPE
   SYNTAX            OCTET STRING (SIZE(1..255))
   MAX-ACCESS        read-only
   STATUS            current
   DESCRIPTION "CMA administrator title."
   ::= { cmaConfigContact 3 }

cmaConfigAdminContactDepartment   OBJECT-TYPE
   SYNTAX            OCTET STRING (SIZE(1..255))
   MAX-ACCESS        read-only
   STATUS            current
   DESCRIPTION "CMA administrator department."
   ::= { cmaConfigContact 4 }

cmaConfigAdminContactCity   OBJECT-TYPE
   SYNTAX            OCTET STRING (SIZE(1..255))
   MAX-ACCESS        read-only
   STATUS            current
   DESCRIPTION "CMA administrator city."
   ::= { cmaConfigContact 5 }

cmaConfigAdminContactPhoneNumber   OBJECT-TYPE
   SYNTAX            OCTET STRING (SIZE(1..255))
   MAX-ACCESS        read-only
   STATUS            current
   DESCRIPTION "CMA administrator phone number."
   ::= { cmaConfigContact 6 }

-- END Admin contact configuration

-- START Log configuration

cmaConfigLogGroup  OBJECT-GROUP
   OBJECTS
   {
      cmaConfigSystemLogLevel
--       cmaConfigGatekeeperLogMessageType,
--       cmaConfigGatekeeperLogMessageEnabled
   }
   STATUS current
   DESCRIPTION "CMA log configuration group."
   ::= { cmaConfigConformance 3 }

-- CmaConfigGatekeeperLogSettingEntry  ::= SEQUENCE
-- {
--    cmaConfigGatekeeperLogMessageType      CmaConfigGatekeeperMessageType,
--    cmaConfigGatekeeperLogMessageEnabled   TruthValue   
-- }

cmaConfigSystemLogLevel   OBJECT-TYPE
   SYNTAX            CmaConfigSystemLogLevel
   MAX-ACCESS        read-only
   STATUS            current
   DESCRIPTION "CMA system log level setting."
   ::= { cmaConfigLog 1 }

-- cmaConfigGatekeeperLogSettingTable      OBJECT-TYPE
--    SYNTAX        SEQUENCE OF CmaConfigGatekeeperLogSettingEntry
--    MAX-ACCESS    not-accessible
--    STATUS        current
--    DESCRIPTION   "CMA gatekeeper log setting table. Contains log setting 
--                   information for each gatekeeper message type." 
--    ::= { cmaConfigLog 2 }

-- cmaConfigGatekeeperLogSettingEntry      OBJECT-TYPE
--    SYNTAX        CmaConfigGatekeeperLogSettingEntry
--    MAX-ACCESS    not-accessible
--    STATUS        current
--    DESCRIPTION   "CMA gatekeeper log setting entry."
--    INDEX         { cmaConfigGatekeeperLogMessageType }
--    ::= { cmaConfigGatekeeperLogSettingTable 1}

-- cmaConfigGatekeeperLogMessageType         OBJECT-TYPE
--    SYNTAX        CmaConfigGatekeeperMessageType
--    MAX-ACCESS    read-only
--    STATUS        current
--    DESCRIPTION   "Message type of the gatekeeper log setting entry."
--    ::= { cmaConfigGatekeeperLogSettingEntry 2 }

-- cmaConfigGatekeeperLogMessageEnabled         OBJECT-TYPE
--    SYNTAX        TruthValue
--    MAX-ACCESS    read-only
--    STATUS        current
--    DESCRIPTION   "Flag indicating whether this message type is logged."
--    ::= { cmaConfigGatekeeperLogSettingEntry 3 }

-- END Log contact configuration


-- START LDAP configuration

cmaConfigLdapGroup  OBJECT-GROUP
   OBJECTS
   {
      cmaConfigLdapEnabled,
      cmaConfigLdapServerInetAddressType,
      cmaConfigLdapServerInetAddress,
      cmaConfigLdapSecurityLevel,
      cmaConfigLdapIgnoreDisabledADUsers,
      cmaConfigLdapExclusionFilter,
      cmaConfigLdapSearchBaseDN,
      cmaConfigLdapWindowsAuthenticationIntegration,
      cmaConfigLdapWindowsAuthenticationDomainControllerName
   }
   STATUS current
   DESCRIPTION "CMA LDAP configuration conformance group."
   ::= { cmaConfigConformance 4 }

cmaConfigLdapEnabled  OBJECT-TYPE
   SYNTAX            TruthValue
   MAX-ACCESS        read-only
   STATUS            current
   DESCRIPTION "LDAP integration enabled flag."
   ::= { cmaConfigLDAP 1 }

cmaConfigLdapServerInetAddressType  OBJECT-TYPE
   SYNTAX            InetAddressType
   MAX-ACCESS        read-only
   STATUS            current
   DESCRIPTION "IP address type of the LDAP server."
   ::= { cmaConfigLDAP 2 }

cmaConfigLdapServerInetAddress  OBJECT-TYPE
   SYNTAX            InetAddress
   MAX-ACCESS        read-only
   STATUS            current
   DESCRIPTION "IP address or DNS name of the LDAP server."
   ::= { cmaConfigLDAP 3 }

cmaConfigLdapSecurityLevel  OBJECT-TYPE
   SYNTAX            CmaConfigLdapSecurityLevel
   MAX-ACCESS        read-only
   STATUS            current
   DESCRIPTION "LDAP security level."
   ::= { cmaConfigLDAP 4 }

cmaConfigLdapIgnoreDisabledADUsers  OBJECT-TYPE
   SYNTAX            TruthValue
   MAX-ACCESS        read-only
   STATUS            current
   DESCRIPTION "Flag indicating whether to ignore disabled active directory users."
   ::= { cmaConfigLDAP 5 }

cmaConfigLdapExclusionFilter  OBJECT-TYPE
   SYNTAX            OCTET STRING (SIZE(0..255))
   MAX-ACCESS        read-only
   STATUS            current
   DESCRIPTION "LDAP exclusion filter."
   ::= { cmaConfigLDAP 6 }

cmaConfigLdapSearchBaseDN  OBJECT-TYPE
   SYNTAX            OCTET STRING (SIZE(0..255))
   MAX-ACCESS        read-only
   STATUS            current
   DESCRIPTION "LDAP search base distinquished name."
   ::= { cmaConfigLDAP 7 }

cmaConfigLdapWindowsAuthenticationIntegration  OBJECT-TYPE
   SYNTAX            TruthValue
   MAX-ACCESS        read-only
   STATUS            current
   DESCRIPTION "Windows Authentication integration flag." 
   ::= { cmaConfigLDAP 8 }

cmaConfigLdapWindowsAuthenticationDomainControllerName  OBJECT-TYPE
   SYNTAX            OCTET STRING (SIZE(0..255))
   MAX-ACCESS        read-only
   STATUS            current
   DESCRIPTION "Windows domain controller name." 
   ::= { cmaConfigLDAP 9 }

-- END LDAP contact configuration


-- START database configuration

-- cmaConfigDatabaseGroup  OBJECT-GROUP
--    OBJECTS
--    {
--       cmaConfigDatabaseType,
--       cmaConfigExternalDatabaseInetAddressType,
--       cmaConfigExternalDatabaseInetAddress,
--       cmaConfigExternalDatabasePort
--    }
--    STATUS current
--    DESCRIPTION "CMA database configuration conformance group."
--    ::= { cmaConfigConformance 5 }

-- cmaConfigDatabaseType   OBJECT-TYPE
--    SYNTAX        CmaConfigDatabaseType
--    MAX-ACCESS    read-only
--    STATUS        current
--    DESCRIPTION   "CMA database type (internal or external)."
--    ::= { cmaConfigDatabase 1 }

-- cmaConfigExternalDatabaseInetAddressType   OBJECT-TYPE
--    SYNTAX        InetAddressType
--    MAX-ACCESS    read-only
--    STATUS        current
--    DESCRIPTION   "IP address type of external database (only valid
--                   if external database is being used)."
--    ::= { cmaConfigDatabase 2 }

-- cmaConfigExternalDatabaseInetAddress   OBJECT-TYPE
--    SYNTAX        InetAddress
--    MAX-ACCESS    read-only
--    STATUS        current
--    DESCRIPTION   "IP address of external database (only valid if
--                   external database is being used)."
--    ::= { cmaConfigDatabase 3 }

-- cmaConfigExternalDatabasePort   OBJECT-TYPE
--    SYNTAX        InetPortNumber
--    MAX-ACCESS    read-only
--    STATUS        current
--    DESCRIPTION   "IP port of external database (only valid if external
--                   database is being used)."
--    ::= { cmaConfigDatabase 4 }

-- END database configuration

-- START system time configuration

cmaConfigSystemTimeGroup  OBJECT-GROUP
   OBJECTS
   {
      cmaConfigSystemTimeZone,
      cmaConfigSystemTimeDaylightSavingAutoAdjust,
      cmaConfigSystemTimeSourceType,
--       cmaConfigSystemTimeExternalSourceSyncPeriod,
      timeSourceIndex,
      timeSourceInetAddressType,
      timeSourceInetAddress
   }
   STATUS current
   DESCRIPTION "CMA System time configuration conformance group."
   ::= { cmaConfigConformance 6 }

cmaConfigSystemTimeZone   OBJECT-TYPE
   SYNTAX        CmaTimeZone
   MAX-ACCESS    read-only
   STATUS        current
   DESCRIPTION   "Time zone in which the CMA server resides."
   ::= { cmaConfigTime 1 }

cmaConfigSystemTimeDaylightSavingAutoAdjust   OBJECT-TYPE
   SYNTAX        TruthValue
   MAX-ACCESS    read-only
   STATUS        current
   DESCRIPTION   "Daylight saving auto adjust flag."
   ::= { cmaConfigTime 2 }

cmaConfigSystemTimeSourceType   OBJECT-TYPE
   SYNTAX        CmaConfigSystemTimeSourceType
   MAX-ACCESS    read-only
   STATUS        current
   DESCRIPTION   "Time source type."
   ::= { cmaConfigTime 3 }

-- cmaConfigSystemTimeExternalSourceSyncPeriod   OBJECT-TYPE
--    SYNTAX        Integer32
--    MAX-ACCESS    read-only
--    STATUS        current
--    DESCRIPTION   "Number of minutes between synchronization attempts with external
--                   time source (only valid if external time source is used)."
--    ::= { cmaConfigTime 4 }

CmaConfigSystemTimeExternalSourceTableEntry ::= SEQUENCE
{
   timeSourceIndex               CmaDefaultTableIndexRange,      
   timeSourceInetAddressType     InetAddressType,
   timeSourceInetAddress         InetAddress
}

cmaConfigSystemTimeExternalSourceTable      OBJECT-TYPE
   SYNTAX        SEQUENCE OF CmaConfigSystemTimeExternalSourceTableEntry
   MAX-ACCESS    not-accessible
   STATUS        current
   DESCRIPTION   "External time source table. Contains time server addresses."
   ::= { cmaConfigTime 5 }

cmaConfigSystemTimeExternalSourceEntry      OBJECT-TYPE
   SYNTAX        CmaConfigSystemTimeExternalSourceTableEntry
   MAX-ACCESS    not-accessible
   STATUS        current
   DESCRIPTION   "External time source table entry."
   INDEX         { timeSourceIndex }
   ::= { cmaConfigSystemTimeExternalSourceTable 1}

timeSourceIndex OBJECT-TYPE
   SYNTAX      CmaDefaultTableIndexRange
   MAX-ACCESS  read-only
   STATUS      current
   DESCRIPTION "Unique system-assigned ID for this entry."
   ::= { cmaConfigSystemTimeExternalSourceEntry 1 }

timeSourceInetAddressType   OBJECT-TYPE
   SYNTAX        InetAddressType
   MAX-ACCESS    read-only
   STATUS        current
   DESCRIPTION   "IP address type of the external time source."
   ::= { cmaConfigSystemTimeExternalSourceEntry 2 }

timeSourceInetAddress   OBJECT-TYPE
   SYNTAX        InetAddress
   MAX-ACCESS    read-only
   STATUS        current
   DESCRIPTION   "IP address or DNS name of the external time source."
   ::= { cmaConfigSystemTimeExternalSourceEntry 3 }

-- END system time configuration

-- START Redundancy settings

cmaConfigRedundancyGroup  OBJECT-GROUP
   OBJECTS
   {
      cmaConfigRedundancyEnabled,
      cmaConfigRedundancyVirtualInetAddressType,
      cmaConfigRedundancyVirtualInetAddress
   }
   STATUS current
   DESCRIPTION "CMA redundancy configuration conformance group."
   ::= { cmaConfigConformance 7 }

cmaConfigRedundancyEnabled   OBJECT-TYPE
   SYNTAX        TruthValue
   MAX-ACCESS    read-only
   STATUS        current
   DESCRIPTION   "Redundancy enabled flag."
   ::= { cmaConfigRedundancy 1 }

cmaConfigRedundancyVirtualInetAddressType   OBJECT-TYPE
   SYNTAX        InetAddressType
   MAX-ACCESS    read-only
   STATUS        current
   DESCRIPTION   "IP address type of the virtual IP (valid only
                  if redundancy is enabled)."
   ::= { cmaConfigRedundancy 2 }

cmaConfigRedundancyVirtualInetAddress   OBJECT-TYPE
   SYNTAX        InetAddress
   MAX-ACCESS    read-only
   STATUS        current
   DESCRIPTION   "IP address of the virtual IP (valid only
                  if redundancy is enabled)."
   ::= { cmaConfigRedundancy 3 }

-- END Redundancy settings


-- START Remote Alert Settings

cmaConfigRemoteAlertGroup  OBJECT-GROUP
   OBJECTS
   {
      cmaConfigRemoteAlertsEnabled,
      cmaConfigRemoteStartupQuiescentTime,
      cmaConfigSystemAlertType,
      cmaConfigSystemAlertLevel,
      cmaConfigEndpointAlertType,
      cmaConfigEndpointAlertLevel
   }
   STATUS current
   DESCRIPTION "CMA remote alert configuration conformance group."
   ::= { cmaConfigConformance 8 }

cmaConfigRemoteAlertsEnabled   OBJECT-TYPE
   SYNTAX        TruthValue
   MAX-ACCESS    read-only
   STATUS        current
   DESCRIPTION   "Remote alerts enabled flag."
   ::= { cmaConfigRemoteAlert 1 }

cmaConfigRemoteStartupQuiescentTime   OBJECT-TYPE
   SYNTAX        Integer32
   MAX-ACCESS    read-only
   STATUS        current
   DESCRIPTION   "Number of minutes after a startup of CMA before remote alerts are sent 
                  (only valid if remote alerts are enabled). This period of time allows the 
                  CMA server to finish startup activities. Only alerts that are still 
                  outstanding at the end of the period are sent."
   ::= { cmaConfigRemoteAlert 2 }

CmaConfigSystemAlertSettingEntry ::= SEQUENCE
{
   cmaConfigSystemAlertType              CmaSystemAlertType,
   cmaConfigSystemAlertLevel             CmaConfigRemoteAlertLevel
}

cmaConfigSystemAlertSettingTable      OBJECT-TYPE
   SYNTAX        SEQUENCE OF CmaConfigSystemAlertSettingEntry
   MAX-ACCESS    not-accessible
   STATUS        current
   DESCRIPTION   "System alert level settings table. Contains system alert types 
                  and their alert levels." 
   ::= { cmaConfigRemoteAlert 3 }

cmaConfigSystemAlertSettingEntry      OBJECT-TYPE
   SYNTAX        CmaConfigSystemAlertSettingEntry
   MAX-ACCESS    not-accessible
   STATUS        current
   DESCRIPTION   "System alert level settings table entry."
   INDEX         { cmaConfigSystemAlertType }
   ::= { cmaConfigSystemAlertSettingTable 1}

cmaConfigSystemAlertType         OBJECT-TYPE
   SYNTAX        CmaSystemAlertType
   MAX-ACCESS    read-only 
   STATUS        current
   DESCRIPTION   "System alert type."
   ::= { cmaConfigSystemAlertSettingEntry 1 }

cmaConfigSystemAlertLevel         OBJECT-TYPE
   SYNTAX        CmaConfigRemoteAlertLevel
   MAX-ACCESS    read-only
   STATUS        current
   DESCRIPTION   "Alert level of the system alert type."
   ::= { cmaConfigSystemAlertSettingEntry 2 }


CmaConfigEndpointAlertSettingEntry ::= SEQUENCE
{
   cmaConfigEndpointAlertType            CmaEndpointAlertType,
   cmaConfigEndpointAlertLevel           CmaConfigRemoteAlertLevel
}

cmaConfigEndpointAlertSettingTable      OBJECT-TYPE
   SYNTAX        SEQUENCE OF CmaConfigEndpointAlertSettingEntry
   MAX-ACCESS    not-accessible
   STATUS        current
   DESCRIPTION   "Endpoint alert level settings table. Contains endpoint alert types 
                  and their alert levels." 
   ::= { cmaConfigRemoteAlert 4 }

cmaConfigEndpointAlertSettingEntry      OBJECT-TYPE
   SYNTAX        CmaConfigEndpointAlertSettingEntry
   MAX-ACCESS    not-accessible
   STATUS        current
   DESCRIPTION   "Endpoint alert level settings table entry."
   INDEX         { cmaConfigEndpointAlertType }
   ::= { cmaConfigEndpointAlertSettingTable 1}

cmaConfigEndpointAlertType         OBJECT-TYPE
   SYNTAX        CmaEndpointAlertType
   MAX-ACCESS    read-only
   STATUS        current
   DESCRIPTION   "Endpoint alert type."
   ::= { cmaConfigEndpointAlertSettingEntry 1 }

cmaConfigEndpointAlertLevel         OBJECT-TYPE
   SYNTAX        CmaConfigRemoteAlertLevel
   MAX-ACCESS    read-only
   STATUS        current
   DESCRIPTION   "Alert level of the endpoint alert type."
   ::= { cmaConfigEndpointAlertSettingEntry 2 }

-- END Remote Alert Settings

-- START Network settings

cmaConfigNetworkGroup  OBJECT-GROUP
   OBJECTS
   {
      cmaConfigNetworkSystemName,
      cmaConfigNetworkInetAddressType,
      cmaConfigNetworkInetAddress,
      cmaConfigNetworkSubnetMask,
      cmaConfigNetworkDefaultGatewayInetAddressType,
      cmaConfigNetworkDefaultGatewayInetAddress,
      cmaConfigNetworkPreferedDnsServerInetAddressType,
      cmaConfigNetworkPreferedDnsServerInetAddress,
      cmaConfigNetworkAlternateDnsServerInetAddressType,
      cmaConfigNetworkAlternateDnsServerInetAddress,
      cmaConfigNetworkDnsServerDomain
   }
   STATUS current
   DESCRIPTION "CMA Network configuration conformance group."
   ::= { cmaConfigConformance 10 }

cmaConfigNetworkSystemName         OBJECT-TYPE
   SYNTAX        OCTET STRING (SIZE(1..255))
   MAX-ACCESS    read-only
   STATUS        current
   DESCRIPTION   "CMA server's system name." 
   ::= { cmaConfigNetwork 1 }

cmaConfigNetworkInetAddressType         OBJECT-TYPE
   SYNTAX        InetAddressType
   MAX-ACCESS    read-only
   STATUS        current
   DESCRIPTION   "CMA server's IP address type." 
   ::= { cmaConfigNetwork 2 }

cmaConfigNetworkInetAddress         OBJECT-TYPE
   SYNTAX        InetAddress
   MAX-ACCESS    read-only
   STATUS        current
   DESCRIPTION   "CMA server's IP address." 
   ::= { cmaConfigNetwork 3 }

cmaConfigNetworkSubnetMask      OBJECT-TYPE
   SYNTAX        InetAddress
   MAX-ACCESS    read-only
   STATUS        current
   DESCRIPTION   "CMA server's subnet mask." 
   ::= { cmaConfigNetwork 4 }

cmaConfigNetworkDefaultGatewayInetAddressType  OBJECT-TYPE
   SYNTAX        InetAddressType
   MAX-ACCESS    read-only
   STATUS        current
   DESCRIPTION   "Default gateway IP address type." 
   ::= { cmaConfigNetwork 5 }

cmaConfigNetworkDefaultGatewayInetAddress  OBJECT-TYPE
   SYNTAX        InetAddress
   MAX-ACCESS    read-only
   STATUS        current
   DESCRIPTION   "Default gateway IP address." 
   ::= { cmaConfigNetwork 6 }

cmaConfigNetworkPreferedDnsServerInetAddressType  OBJECT-TYPE
   SYNTAX        InetAddressType
   MAX-ACCESS    read-only
   STATUS        current
   DESCRIPTION   "Prefered DNS server IP address type." 
   ::= { cmaConfigNetwork 7 }

cmaConfigNetworkPreferedDnsServerInetAddress  OBJECT-TYPE
   SYNTAX        InetAddress
   MAX-ACCESS    read-only
   STATUS        current
   DESCRIPTION   "Prefered DNS server IP address." 
   ::= { cmaConfigNetwork 8 }

cmaConfigNetworkAlternateDnsServerInetAddressType  OBJECT-TYPE
   SYNTAX        InetAddressType
   MAX-ACCESS    read-only
   STATUS        current
   DESCRIPTION   "Alternate DNS server IP address type." 
   ::= { cmaConfigNetwork 9 }

cmaConfigNetworkAlternateDnsServerInetAddress  OBJECT-TYPE
   SYNTAX        InetAddress
   MAX-ACCESS    read-only
   STATUS        current
   DESCRIPTION   "Alternate DNS server IP address." 
   ::= { cmaConfigNetwork 10 }

cmaConfigNetworkDnsServerDomain  OBJECT-TYPE
   SYNTAX        OCTET STRING (SIZE(0..255))
   MAX-ACCESS    read-only
   STATUS        current
   DESCRIPTION   "DNS server domain name." 
   ::= { cmaConfigNetwork 11 }

-- END  Network settings

-- START email settings
cmaConfigEmailGroup  OBJECT-GROUP
   OBJECTS
   {
      cmaConfigEmailCount,
      emailConfigIndex,
      cmaConfigEmailFromAddress,
      cmaConfigEmailSmtpServerInetAddressType,
      cmaConfigEmailSmtpServerInetAddress
   }
   STATUS current
   DESCRIPTION "CMA email configuration conformance group."
   ::= { cmaConfigConformance 11 }


cmaConfigEmailCount OBJECT-TYPE
   SYNTAX      Integer32
   MAX-ACCESS  read-only
   STATUS      current
   DESCRIPTION "Number of email configurations." 
   ::= { cmaConfigEmail 1 }

EmailConfigTableEntry    ::= SEQUENCE
{
   emailConfigIndex                        CmaDefaultTableIndexRange,
   cmaConfigEmailFromAddress               OCTET STRING,
   cmaConfigEmailSmtpServerInetAddressType InetAddressType,
   cmaConfigEmailSmtpServerInetAddress     InetAddress
}

cmaConfigEmailTable OBJECT-TYPE
   SYNTAX        SEQUENCE OF EmailConfigTableEntry
   MAX-ACCESS    not-accessible
   STATUS        current
   DESCRIPTION   "Email configration table. "
   ::= { cmaConfigEmail 2 }

emailConfigTableEntry OBJECT-TYPE
   SYNTAX        EmailConfigTableEntry
   MAX-ACCESS    not-accessible
   STATUS        current
   DESCRIPTION   "Email config entry."
   INDEX         { emailConfigIndex }
   ::= { cmaConfigEmailTable 1 }

emailConfigIndex OBJECT-TYPE
   SYNTAX      CmaDefaultTableIndexRange
   MAX-ACCESS  read-only
   STATUS      current
   DESCRIPTION "Unique system-assigned ID for this entry." 
   ::= { emailConfigTableEntry 1 }

cmaConfigEmailFromAddress  OBJECT-TYPE
   SYNTAX        OCTET STRING (SIZE(0..255))
   MAX-ACCESS    read-only
   STATUS        current
   DESCRIPTION   "CMA server's email 'From' address." 
   ::= { emailConfigTableEntry 2 }

cmaConfigEmailSmtpServerInetAddressType  OBJECT-TYPE
   SYNTAX        InetAddressType
   MAX-ACCESS    read-only
   STATUS        current
   DESCRIPTION   "IP address type of the SMTP server." 
   ::= { emailConfigTableEntry 3 }

cmaConfigEmailSmtpServerInetAddress  OBJECT-TYPE
   SYNTAX        InetAddress
   MAX-ACCESS    read-only
   STATUS        current
   DESCRIPTION   "IP address of the SMTP server." 
   ::= { emailConfigTableEntry 4 }

-- END email settings

-- START UI Settings
cmaConfigUIGroup  OBJECT-GROUP
   OBJECTS
   {
      cmaConfigUIDefaultProfileAccessAllowed,
      cmaConfigUIMaxSessionPerUser
   }
   STATUS current
   DESCRIPTION "CMA UI configuration conformance group."
   ::= { cmaConfigConformance 12 }

cmaConfigUIDefaultProfileAccessAllowed OBJECT-TYPE
   SYNTAX      TruthValue
   MAX-ACCESS  read-only
   STATUS      current
   DESCRIPTION "Flag indicating whether users without explicit roles are allowed to log into 
                the CMA UI and are assigned the default profile."
   ::= { cmaConfigUI 1 }

cmaConfigUIMaxSessionPerUser OBJECT-TYPE
   SYNTAX      Integer32
   MAX-ACCESS  read-only
   STATUS      current
   DESCRIPTION "The Maximum Number of Sessions allowed per user. The default and minimum 
                value is 1.It returns a 0 if disabled."
   ::= { cmaConfigUI 2 }

-- END UI Settings

-- START endpoint management settings
cmaConfigEndpointGroup  OBJECT-GROUP
   OBJECTS
   {
      cmaConfigEndpointAutoDiscovery,
      cmaConfigEndpointUseCommonPassword
   }
   STATUS current
   DESCRIPTION "CMA Endpoint management configuration conformance group."
   ::= { cmaConfigConformance 13 }

cmaConfigEndpointAutoDiscovery OBJECT-TYPE
   SYNTAX      TruthValue
   MAX-ACCESS  read-only
   STATUS      current
   DESCRIPTION "Flag indicating whether automatic endpoint discovery is enabled."
   ::= { cmaConfigEndpoint 1 }

cmaConfigEndpointUseCommonPassword OBJECT-TYPE
   SYNTAX      TruthValue
   MAX-ACCESS  read-only
   STATUS      current
   DESCRIPTION "Flag indicating whether a common administrator password is used for 
                all endpoints."
   ::= { cmaConfigEndpoint 2 }

-- END endpoint management settings

-- START Dial Plans - dial rules
cmaConfigSiteGroup  OBJECT-GROUP
   OBJECTS
   {
      sitetopologySiteProvisioningCount,
      siteProvisioningSiteName,
      siteCountry,
      siteDateFormat,
      siteAutoAdjustDst,
      siteTimeFormat ,
      siteTimeServerUpdateType,
      sitePrimaryTimeServerInetAddressType,
      sitePrimaryTimeServerInetAddress,
      siteSecondaryTimeServerInetAddressType,
      siteSecondaryTimeServerInetAddress,
      siteTimeZone,
      siteFirewallUseFixedPorts,
      siteFirewallTcpStartPort,
      siteFirewallUdpStartPort,
      siteFirewallH460Traversal,
      siteFirewallNatConfiguration,
      siteFirewallNatWanAddressType,
      siteFirewallNatWanAddress,
      siteFirewallNatH323Compatible,
      siteFirewallShowEpInGab,
      siteFirewallEnableSipKeepAlives,
      siteH323EnableIpCalls,
      siteH323GatekeeperIPAddressType,
      siteH323GatekeeperIPAddress,
      siteH3232UseGkForMultipointCalls,
      siteProvisioningPollingInterval,
      siteSoftupdatePollingInterval,
      siteQosVideoTosValue,
      siteQosAudioTosValue,
      siteQosFeccTosValue,
      siteQosTosType,
      siteQosMaxMtuSize,
      siteQosEnablePvec,
      siteQosEnableRsvp,
      siteQosDynamicBandwidth,
      siteQosMaxTransmitBandwidth,
      siteQosMaxReceiveBandwidth,
      siteSecurityUsePwdForRemoteAccess,
      siteSecurityEnableSecureMode,
      siteSecurityEnableEncryption,
      siteSecurityEnableWebAccess,
      siteSecurityEnableTelnetAccess,
      siteSecurityEnableSnmpAccess,
      siteSecurityWebAccessPort,
      siteSecurityAllowWebVideoDisplay,
      siteSecurityNtlmVersion,
      siteCmadHeartbeatPollingInterval,
      siteCmadInCallStatsPollingInterval,
      siteCalendaringExchangeServerIPAddressType,
      siteCalendaringExchangeServerIPAddress,
      siteSIPEnable,
      siteSIPDomain,
      siteSIPAutoDiscoverServer,
      siteSIPProxyServerInetAddressType,
      siteSIPProxyServerInetAddress,
      siteSIPRegistrarServerInetAddressType,
      siteSIPRegistrarServerInetAddress,
      siteSIPBackupProxyServerInetAddressType,
      siteSIPBackupProxyServerInetAddress,
      siteSIPBackupRegistrarServerInetAddressType,
      siteSIPBackupRegistrarServerInetAddress,
      siteSIPTransportLayerProtocol,
      siteSIPServerType,                            
      siteSIPVerifyCertificate,
      siteSIPUseEnterpriseCredentials,
      siteSecurityProfile,                              
      siteSecurityIdleSessionTimeout,           
      siteSecurityFailedLoginThreshold,
      siteSecurityFailedLoginWindow,
      siteSecurityPortLockoutDuration,          
      siteSecurityMaxCertificateVerificationDepth,
      siteSecurityVerifyCertforWebAccess,               
      siteWhitelistIPEnable,                    
--      siteEnableEnterpriseDir,                  
      siteEnterpriseDirAdminGroup,                      
      siteEnterpriseDirUserGroup,
      siteDirectorySettingsUseThisServer,
      siteDirectorySettingsServerIPAddress,
      siteDirectorySettingsVerifyCertificate,
      sitePresenceSettingsUseThisServer,
      sitePresenceSettingsServerIPAddress,
      sitePresenceSettingsVerifyCertificate,
      sitetopologyRPADSiteProvisioningCount,
      rpadsiteProvisioningSiteName,
      rpadsiteTimeServerUpdateType,
      rpadsitePrimaryTimeServerInetAddressType,
      rpadsitePrimaryTimeServerInetAddress,
      rpadsiteSecondaryTimeServerInetAddressType,
      rpadsiteSecondaryTimeServerInetAddress,
      rpadsiteProvisioningPollingInterval,
      rpadsiteCmadHeartbeatPollingInterval,
      rpadserverStatusPollingInterval,
      rpadsiteH323EnableIpCalls,
      rpadsiteH323GatekeeperIPAddressType,
      rpadsiteH323GatekeeperIPAddress,
      rpadsiteSIPEnable,
      rpadsiteSIPProxyServerInetAddressType,
      rpadsiteSIPProxyServerInetAddress,
      rpadsiteSIPRegistrarServerInetAddressType,
      rpadsiteSIPRegistrarServerInetAddress,
      rpadsiteSIPTransportLayerProtocol,
      rpadsiteSIPVerifyCertificate,
      rpadsiteDirectorySettingsUseThisServer,
      rpadsiteDirectorySettingsServerIPAddress,
      rpadsiteDirectorySettingsVerifyCertificate,
      rpadsitePresenceSettingsUseThisServer,
      rpadsitePresenceSettingsServerIPAddress,
      rpadsitePresenceSettingsVerifyCertificate     
   }
   STATUS current
   DESCRIPTION "CMA Dial plan configuration conformance group."
   ::= { cmaConfigConformance 14 }


-- START Site Topology

cmaConfigSiteTopologyGroup  OBJECT-GROUP
   OBJECTS
   {
      siteTopoSiteCount,
      siteIndex,
      siteName, 
      siteDescription,
      siteOverrideItuDialingRules,
      sitePbxAccessCode,
      siteCountryCode,
      siteAreaCode,
      siteNumSubscriberDigits,
      siteIsdnNumberAssignmentMethod,
      siteInternetRoutingType,
      siteSendDialStringtoSBCorALG,
      siteCallSignallingInetAddressType,
      siteCallSignallingInetAddress,
      siteSubnetCount,
      siteIsdnGatewayPhoneNumber,
      siteIsdnE164Start,
      siteIsdnE164End,
      siteIsdnCliDigits,
      siteIsdnShortPhoneDigits,
      siteIsdnNumberRangeList,
      siteType,
      siteLocation,
      siteLongitude,
      siteLatitude,
      siteTerritory,
      
      siteTopoSubnetCount,
      subnetIndex,
      subnetName,
      subnetSiteName,
      subnetIpAddress,
      subnetMaskSize,
      subnetTotalBandwidthRestriction,
      subnetTotalBandwidthRestrictionEnabled,
      subnetMaxBitRateRestriction,
      subnetMaxBitRateRestrictionEnabled,

      siteTopoSiteLinkCount,
      siteLinkIndex,
      siteLinkName,
      siteLinkDescription,
      siteLinkSiteA,              
      siteLinkSiteB,
      siteLinkTotalBandwidthRestriction,
      siteLinkTotalBandwidthRestrictionEnabled,
      siteLinkMaxBitRateRestriction,
      siteLinkMaxBitRateRestrictionEnabled,
      
      siteTopoCloudCount,
      cloudIndex,
      cloudName,
      cloudDescription,

      siteTopoTerritoryCount,
      territoryIndex,
      territoryName,
      territoryDescription,
      territoryPrimaryCluster,
      territoryBackupCluster,
      territoryHostConferenceRooms,
      
      siteTopoSiteToSiteExclusionCount,
      siteToSiteExclusionIndex,
      siteToSiteExclusionSiteA,
      siteToSiteExclusionSiteB
   }
   
   STATUS current
   DESCRIPTION "CMA Site topology configuration conformance group."
   ::= { cmaConfigConformance 15 }

-- Sites

siteTopoSiteCount OBJECT-TYPE
   SYNTAX      Integer32
   MAX-ACCESS  read-only
   STATUS      current
   DESCRIPTION "Number of configured sites." 
   ::= { cmaConfigSiteTopology 1 }

SiteTopoSiteTableEntry    ::= SEQUENCE
{
   siteIndex                            CmaDefaultTableIndexRange,
   siteName                             OCTET STRING,
   siteDescription                      OCTET STRING,
   siteOverrideItuDialingRules          TruthValue,
   sitePbxAccessCode                    OCTET STRING,
   siteCountryCode                      OCTET STRING,
   siteAreaCode                         OCTET STRING,
   siteNumSubscriberDigits              Integer32,
   siteIsdnNumberAssignmentMethod       SiteTopoIsdnNumberAssignmentMethodType,
   siteInternetRoutingType              SiteTopoInternetRoutingType,
   siteSendDialStringtoSBCorALG          TruthValue,
   siteCallSignallingInetAddressType    InetAddressType,
   siteCallSignallingInetAddress        InetAddress,
   siteSubnetCount                      Integer32,
   siteIsdnGatewayPhoneNumber           OCTET STRING,
   siteIsdnE164Start                    OCTET STRING,
   siteIsdnE164End                      OCTET STRING,
   siteIsdnCliDigits                    Integer32,
   siteIsdnShortPhoneDigits             Integer32,
   siteIsdnNumberRangeList              OCTET STRING,
   siteType                             SiteTopoSiteType,
   siteLocation                         OCTET STRING,
   siteLongitude                        OCTET STRING,
   siteLatitude                         OCTET STRING,
   siteTerritory                        OCTET STRING
   }

siteTopoSiteTable OBJECT-TYPE
   SYNTAX        SEQUENCE OF SiteTopoSiteTableEntry
   MAX-ACCESS    not-accessible
   STATUS        current
   DESCRIPTION   "Site topology site table. Lists the sites defined in the system 
                  and their parameters."
   ::= { cmaConfigSiteTopology 2 }

siteTopoSiteTableEntry OBJECT-TYPE
   SYNTAX        SiteTopoSiteTableEntry
   MAX-ACCESS    not-accessible
   STATUS        current
   DESCRIPTION   "Site table entry."
   INDEX         { siteIndex }
   ::= { siteTopoSiteTable 1 }

siteIndex OBJECT-TYPE
   SYNTAX      CmaDefaultTableIndexRange
   MAX-ACCESS  read-only
   STATUS      current
   DESCRIPTION "Unique system-assigned ID for this entry." 
   ::= { siteTopoSiteTableEntry 1 }

siteName OBJECT-TYPE
   SYNTAX      OCTET STRING (SIZE(1..255)) 
   MAX-ACCESS  read-only
   STATUS      current
   DESCRIPTION "Name of the site."
   ::= { siteTopoSiteTableEntry 2 }

siteDescription OBJECT-TYPE
   SYNTAX      OCTET STRING (SIZE(1..255)) 
   MAX-ACCESS  read-only
   STATUS      current
   DESCRIPTION "Description of the site."
   ::= { siteTopoSiteTableEntry 3 }

siteOverrideItuDialingRules OBJECT-TYPE
   SYNTAX      TruthValue
   MAX-ACCESS  read-only
   STATUS      current
   DESCRIPTION "Flag indicating whether to override ITU dialing rules  
                for the site."
   DEFVAL      { false }
   ::= { siteTopoSiteTableEntry 4 }

sitePbxAccessCode OBJECT-TYPE
   SYNTAX      OCTET STRING (SIZE(0..10))
   MAX-ACCESS  read-only
   STATUS      current
   DESCRIPTION "Access code required to enter the site's PBX system."
   DEFVAL      { "" }
   ::= { siteTopoSiteTableEntry 5 }

siteCountryCode OBJECT-TYPE
   SYNTAX      OCTET STRING (SIZE(0..10))
   MAX-ACCESS  read-only
   STATUS      current
   DESCRIPTION "Country code for the site."
   DEFVAL      { "" }
   ::= { siteTopoSiteTableEntry 6 }

siteAreaCode OBJECT-TYPE
   SYNTAX      OCTET STRING (SIZE(0..10))
   MAX-ACCESS  read-only
   STATUS      current
   DESCRIPTION "Area code for the site."
   DEFVAL      { "" }
   ::= { siteTopoSiteTableEntry 7 }

siteNumSubscriberDigits OBJECT-TYPE
   SYNTAX      Integer32
   MAX-ACCESS  read-only
   STATUS      current
   DESCRIPTION "Number of digits in a phone number for the site."
   DEFVAL      { 0 }
   ::= { siteTopoSiteTableEntry 8 }

siteIsdnNumberAssignmentMethod OBJECT-TYPE
   SYNTAX      SiteTopoIsdnNumberAssignmentMethodType
   MAX-ACCESS  read-only
   STATUS      current
   DESCRIPTION "ISDN number assignment method for the site."
   DEFVAL      { none }
   ::= { siteTopoSiteTableEntry 9 }

siteInternetRoutingType OBJECT-TYPE
   SYNTAX      SiteTopoInternetRoutingType
   MAX-ACCESS  read-only
   STATUS      current
   DESCRIPTION "Internet calling type for the site."
   DEFVAL      { notAllowed }
   ::= { siteTopoSiteTableEntry 10 }

siteSendDialStringtoSBCorALG OBJECT-TYPE
   SYNTAX      TruthValue
   MAX-ACCESS  read-only
   STATUS      current
   DESCRIPTION "Send unmodified Dial String to Session Border Controller(SBC)
                  or Application Level Gateway(ALG). "
   DEFVAL      { false }
   ::= { siteTopoSiteTableEntry 11 }

siteCallSignallingInetAddressType OBJECT-TYPE
   SYNTAX      InetAddressType
   MAX-ACCESS  read-only
   STATUS      current
   DESCRIPTION "IP address type for the site."
   DEFVAL      { ipv4 }
   ::= { siteTopoSiteTableEntry 12 }

siteCallSignallingInetAddress OBJECT-TYPE
   SYNTAX      InetAddress
   MAX-ACCESS  read-only
   STATUS      current
   DESCRIPTION "IP address for the site."
   DEFVAL      { "" }
   ::= { siteTopoSiteTableEntry 13 }

siteSubnetCount OBJECT-TYPE
   SYNTAX      Integer32
   MAX-ACCESS  read-only
   STATUS      current
   DESCRIPTION "Number of subnets defined for the site."
   DEFVAL      { 0 }
   ::= { siteTopoSiteTableEntry 19 }

siteIsdnGatewayPhoneNumber OBJECT-TYPE
   SYNTAX      OCTET STRING
   MAX-ACCESS  read-only
   STATUS      current
   DESCRIPTION "ISDN gateway phone number for the site."
   DEFVAL      { "" }
   ::= { siteTopoSiteTableEntry 20 }

siteIsdnE164Start OBJECT-TYPE
   SYNTAX      OCTET STRING
   MAX-ACCESS  read-only
   STATUS      current
   DESCRIPTION "Start of the range of E.164 numbers available for 
                automatic assignment to IP devices for the site."
   DEFVAL      { "" }
   ::= { siteTopoSiteTableEntry 21 }

siteIsdnE164End OBJECT-TYPE
   SYNTAX      OCTET STRING
   MAX-ACCESS  read-only
   STATUS      current
   DESCRIPTION "End of the range of E.164 numbers available for 
                automatic assignment to IP devices for the site."
   DEFVAL      { "" }
   ::= { siteTopoSiteTableEntry 22 }

siteIsdnCliDigits OBJECT-TYPE
   SYNTAX      Integer32(0..17)
   MAX-ACCESS  read-only
   STATUS      current
   DESCRIPTION "Number of digits in the Call Line Identifier,
                which is the dialed number for the site."
   DEFVAL      { 0 }
   ::= { siteTopoSiteTableEntry 23 }

siteIsdnShortPhoneDigits OBJECT-TYPE
   SYNTAX      Integer32
   MAX-ACCESS  read-only
   STATUS      current
   DESCRIPTION "Number of digits in the short form of the dialing number 
                for the site. This number indicates what part of the 
                dial string is sent to the gatekeeper for address 
                resolution in gateway + extension dialing."
   DEFVAL      { 0 }
   ::= { siteTopoSiteTableEntry 24 }

siteIsdnNumberRangeList OBJECT-TYPE
   SYNTAX      OCTET STRING
   MAX-ACCESS  read-only
   STATUS      current
   DESCRIPTION "Comma-separated list of ISDN number ranges, specifying the 
                ISDN numbers available for automatic assignment to 
                IP devices for the site (each range has the format 
                startNumber-endNumber)."
   DEFVAL      { "" }
   ::= { siteTopoSiteTableEntry 25 }

siteType OBJECT-TYPE
   SYNTAX      SiteTopoSiteType
   MAX-ACCESS  read-only
   STATUS      current
   DESCRIPTION "Type of site."
   ::= { siteTopoSiteTableEntry 26 }

siteLocation OBJECT-TYPE
   SYNTAX      OCTET STRING
   MAX-ACCESS  read-only
   STATUS      current
   DESCRIPTION "Geo-location of site."
   DEFVAL      { "" }
   ::= { siteTopoSiteTableEntry 27 }

siteLongitude OBJECT-TYPE
   SYNTAX      OCTET STRING
   MAX-ACCESS  read-only
   STATUS      current
   DESCRIPTION "Geographical longitude of site."
   DEFVAL      { "" }
   ::= { siteTopoSiteTableEntry 28 }

siteLatitude OBJECT-TYPE
   SYNTAX      OCTET STRING
   MAX-ACCESS  read-only
   STATUS      current
   DESCRIPTION "Geographical latitude of site."
   DEFVAL      { "" }
   ::= { siteTopoSiteTableEntry 29 }

siteTerritory OBJECT-TYPE
   SYNTAX      OCTET STRING
   MAX-ACCESS  read-only
   STATUS      current
   DESCRIPTION "Territory that site belongs to."
   DEFVAL      { "" }
   ::= { siteTopoSiteTableEntry 30 }

-- Links

siteTopoSiteLinkCount  OBJECT-TYPE
   SYNTAX      Integer32
   MAX-ACCESS  read-only
   STATUS      current
   DESCRIPTION "Number of site links configured in CMA system."
   ::= { cmaConfigSiteTopology 3 }

SiteTopoSiteLinkTableEntry   ::= SEQUENCE
{
   siteLinkIndex                     CmaDefaultTableIndexRange,
   siteLinkName                             OCTET STRING,
   siteLinkDescription                      OCTET STRING,
   siteLinkSiteA                            OCTET STRING,                    
   siteLinkSiteB                            OCTET STRING,
   siteLinkTotalBandwidthRestriction        Counter64,
   siteLinkTotalBandwidthRestrictionEnabled TruthValue,
   siteLinkMaxBitRateRestriction            Counter64,
   siteLinkMaxBitRateRestrictionEnabled     TruthValue
}

siteTopoSiteLinkTable OBJECT-TYPE
   SYNTAX        SEQUENCE OF SiteTopoSiteLinkTableEntry
   MAX-ACCESS    not-accessible
   STATUS        current
   DESCRIPTION   "Site topology site link table. Lists the site links  
                  defined in the system and their parameters."
   ::= { cmaConfigSiteTopology 4 }

siteTopoSiteLinkTableEntry OBJECT-TYPE
   SYNTAX        SiteTopoSiteLinkTableEntry
   MAX-ACCESS    not-accessible
   STATUS        current
   DESCRIPTION   "Site link table entry."
   INDEX         { siteLinkIndex }
   ::= { siteTopoSiteLinkTable 1 }

siteLinkIndex OBJECT-TYPE
   SYNTAX      CmaDefaultTableIndexRange
   MAX-ACCESS  read-only
   STATUS      current
   DESCRIPTION "Unique system-assigned ID for this entry." 
   ::= { siteTopoSiteLinkTableEntry 1 }

siteLinkName OBJECT-TYPE
   SYNTAX      OCTET STRING (SIZE(1..255))
   MAX-ACCESS  read-only
   STATUS      current
   DESCRIPTION "Name of the site link."
   ::= { siteTopoSiteLinkTableEntry 2 }

siteLinkDescription OBJECT-TYPE
   SYNTAX      OCTET STRING (SIZE(1..255))
   MAX-ACCESS  read-only
   STATUS      current
   DESCRIPTION "Description of the site link."
   ::= { siteTopoSiteLinkTableEntry 3 }

siteLinkSiteA OBJECT-TYPE
   SYNTAX      OCTET STRING (SIZE(1..255))
   MAX-ACCESS  read-only
   STATUS      current
   DESCRIPTION "Name of the site of origin for the site link."
   ::= { siteTopoSiteLinkTableEntry 4 }

siteLinkSiteB OBJECT-TYPE
   SYNTAX      OCTET STRING (SIZE(1..255))
   MAX-ACCESS  read-only
   STATUS      current
   DESCRIPTION "Name of the destination site for the site link."
   ::= { siteTopoSiteLinkTableEntry 5 }

siteLinkTotalBandwidthRestriction OBJECT-TYPE
   SYNTAX      Counter64
   MAX-ACCESS  read-only
   STATUS      current
   DESCRIPTION "Total bandwidth restriction for the site link."
   ::= { siteTopoSiteLinkTableEntry 6 }

siteLinkTotalBandwidthRestrictionEnabled OBJECT-TYPE
   SYNTAX      TruthValue
   MAX-ACCESS  read-only
   STATUS      current
   DESCRIPTION "Flag indicating whether bandwidth is restricted  
                for the site link."
   ::= { siteTopoSiteLinkTableEntry 7 }

siteLinkMaxBitRateRestriction OBJECT-TYPE
   SYNTAX      Counter64
   MAX-ACCESS  read-only
   STATUS      current
   DESCRIPTION "Maximum call bit rate for the site link."
   ::= { siteTopoSiteLinkTableEntry 8 }

siteLinkMaxBitRateRestrictionEnabled OBJECT-TYPE
   SYNTAX      TruthValue
   MAX-ACCESS  read-only
   STATUS      current
   DESCRIPTION "Flag indicating whether maximum call rate
                is restricted for the site link."
   ::= { siteTopoSiteLinkTableEntry 9 }

-- Subnets

siteTopoSubnetCount  OBJECT-TYPE
   SYNTAX      Integer32
   MAX-ACCESS  read-only
   STATUS      current
   DESCRIPTION "Number of subnets configured in CMA system."
   ::= { cmaConfigSiteTopology 5 }

SiteTopoSubnetTableEntry   ::= SEQUENCE
{
   subnetIndex                            CmaDefaultTableIndexRange,
   subnetName                             OCTET STRING,
   subnetSiteName                         OCTET STRING,
   subnetIpAddress                        InetAddress,
   subnetMaskSize                         Integer32,
   subnetTotalBandwidthRestriction        Counter64,
   subnetTotalBandwidthRestrictionEnabled TruthValue,
   subnetMaxBitRateRestriction            Counter64,
   subnetMaxBitRateRestrictionEnabled     TruthValue
}

siteTopoSubnetTable OBJECT-TYPE
   SYNTAX        SEQUENCE OF SiteTopoSubnetTableEntry
   MAX-ACCESS    not-accessible
   STATUS        current
   DESCRIPTION   "Site topology subnet table. Lists the subnets  
                  defined in the system and their parameters."
   ::= { cmaConfigSiteTopology 6 }

siteTopoSubnetTableEntry OBJECT-TYPE
   SYNTAX        SiteTopoSubnetTableEntry
   MAX-ACCESS    not-accessible
   STATUS        current
   DESCRIPTION   "Subnet table entry."
   INDEX         { subnetIndex }
   ::= { siteTopoSubnetTable 1 }

subnetIndex OBJECT-TYPE
   SYNTAX      CmaDefaultTableIndexRange
   MAX-ACCESS  read-only
   STATUS      current
   DESCRIPTION "Unique system-assigned ID for this entry." 
   ::= { siteTopoSubnetTableEntry 1 }

subnetName OBJECT-TYPE
   SYNTAX      OCTET STRING (SIZE(1..255)) 
   MAX-ACCESS  read-only
   STATUS      current
   DESCRIPTION "Name of the subnet."
   ::= { siteTopoSubnetTableEntry 2 }

subnetSiteName         OBJECT-TYPE
   SYNTAX        OCTET STRING (SIZE(1..255))
   MAX-ACCESS    read-only
   STATUS        current
   DESCRIPTION   "Name of the subnet's site."
   ::= { siteTopoSubnetTableEntry 3 }

subnetIpAddress OBJECT-TYPE
   SYNTAX      InetAddress
   MAX-ACCESS  read-only
   STATUS      current
   DESCRIPTION "IP address for the subnet."
   ::= { siteTopoSubnetTableEntry 4 }

subnetMaskSize  OBJECT-TYPE
   SYNTAX      Integer32
   MAX-ACCESS  read-only
   STATUS      current
   DESCRIPTION "Bit size of the mask for the subnet."
   ::= { siteTopoSubnetTableEntry 5 }

subnetTotalBandwidthRestriction OBJECT-TYPE
   SYNTAX      Counter64
   MAX-ACCESS  read-only
   STATUS      current
   DESCRIPTION "Bandwidth restriction for the subnet."
   ::= { siteTopoSubnetTableEntry 6 }

subnetTotalBandwidthRestrictionEnabled OBJECT-TYPE
   SYNTAX      TruthValue
   MAX-ACCESS  read-only
   STATUS      current
   DESCRIPTION "Flag indicating whether bandwidth is restricted  
                for the subnet."
   ::= { siteTopoSubnetTableEntry 7 }

subnetMaxBitRateRestriction OBJECT-TYPE
   SYNTAX      Counter64
   MAX-ACCESS  read-only
   STATUS      current
   DESCRIPTION "Maximum call bit rate for the subnet."
   ::= { siteTopoSubnetTableEntry 8 }

subnetMaxBitRateRestrictionEnabled OBJECT-TYPE
   SYNTAX      TruthValue
   MAX-ACCESS  read-only
   STATUS      current
   DESCRIPTION "Flag indicating whether maximum call rate
                is restricted for the subnet."
   ::= { siteTopoSubnetTableEntry 9 }

-- Clouds

siteTopoCloudCount  OBJECT-TYPE
   SYNTAX      Integer32
   MAX-ACCESS  read-only
   STATUS      current
   DESCRIPTION "Number of network clouds configured in CMA system."
   ::= { cmaConfigSiteTopology 7 }

SiteTopoCloudTableEntry   ::= SEQUENCE
{
   cloudIndex                     CmaDefaultTableIndexRange,
   cloudName                      OCTET STRING,
   cloudDescription               OCTET STRING
}

siteTopoCloudTable OBJECT-TYPE
   SYNTAX        SEQUENCE OF SiteTopoCloudTableEntry
   MAX-ACCESS    not-accessible
   STATUS        current
   DESCRIPTION   "Site topology network cloud table. Lists the network clouds  
                  defined in the system and their parameters."
   ::= { cmaConfigSiteTopology 8 }

siteTopoCloudTableEntry OBJECT-TYPE
   SYNTAX        SiteTopoCloudTableEntry
   MAX-ACCESS    not-accessible
   STATUS        current
   DESCRIPTION   "Cloud table entry."
   INDEX         { cloudIndex }
   ::= { siteTopoCloudTable 1 }

cloudIndex OBJECT-TYPE
   SYNTAX      CmaDefaultTableIndexRange
   MAX-ACCESS  read-only
   STATUS      current
   DESCRIPTION "Unique system-assigned ID for this entry." 
   ::= { siteTopoCloudTableEntry 1 }

cloudName OBJECT-TYPE
   SYNTAX      OCTET STRING (SIZE(1..255)) 
   MAX-ACCESS  read-only
   STATUS      current
   DESCRIPTION "Name of the network cloud."
   ::= { siteTopoCloudTableEntry 2 }

cloudDescription        OBJECT-TYPE
   SYNTAX        OCTET STRING (SIZE(1..255))
   MAX-ACCESS    read-only
   STATUS        current
   DESCRIPTION   "Description for the netowrk cloud."
   ::= { siteTopoCloudTableEntry 3 }

-- Territories

siteTopoTerritoryCount  OBJECT-TYPE
   SYNTAX      Integer32
   MAX-ACCESS  read-only
   STATUS      current
   DESCRIPTION "Number of territories configured in CMA system."
   ::= { cmaConfigSiteTopology 9 }

SiteTopoTerritoryTableEntry   ::= SEQUENCE
{
   territoryIndex                     CmaDefaultTableIndexRange,
   territoryName                      OCTET STRING,
   territoryDescription               OCTET STRING,
   territoryPrimaryCluster            OCTET STRING,
   territoryBackupCluster             OCTET STRING,
   territoryHostConferenceRooms       TruthValue
}

siteTopoTerritoryTable OBJECT-TYPE
   SYNTAX        SEQUENCE OF SiteTopoTerritoryTableEntry
   MAX-ACCESS    not-accessible
   STATUS        current
   DESCRIPTION   "Site topology territory table. Lists the territories  
                  defined in the system and their parameters."
   ::= { cmaConfigSiteTopology 10 }

siteTopoTerritoryTableEntry OBJECT-TYPE
   SYNTAX        SiteTopoTerritoryTableEntry
   MAX-ACCESS    not-accessible
   STATUS        current
   DESCRIPTION   "Territory table entry."
   INDEX         { territoryIndex }
   ::= { siteTopoTerritoryTable 1 }

territoryIndex OBJECT-TYPE
   SYNTAX      CmaDefaultTableIndexRange
   MAX-ACCESS  read-only
   STATUS      current
   DESCRIPTION "Unique system-assigned ID for this entry." 
   ::= { siteTopoTerritoryTableEntry 1 }

territoryName OBJECT-TYPE
   SYNTAX      OCTET STRING (SIZE(1..255)) 
   MAX-ACCESS  read-only
   STATUS      current
   DESCRIPTION "Name of the territory."
   ::= { siteTopoTerritoryTableEntry 2 }

territoryDescription        OBJECT-TYPE
   SYNTAX        OCTET STRING (SIZE(1..255))
   MAX-ACCESS    read-only
   STATUS        current
   DESCRIPTION   "Description for the territory."
   ::= { siteTopoTerritoryTableEntry 3 }

territoryPrimaryCluster     OBJECT-TYPE
   SYNTAX        OCTET STRING (SIZE(1..255))
   MAX-ACCESS    read-only
   STATUS        current
   DESCRIPTION   "Primary cluster for the territory."
   ::= { siteTopoTerritoryTableEntry 4 }

territoryBackupCluster      OBJECT-TYPE
   SYNTAX        OCTET STRING (SIZE(1..255))
   MAX-ACCESS    read-only
   STATUS        current
   DESCRIPTION   "Backup cluster for the territory."
   ::= { siteTopoTerritoryTableEntry 5 }

territoryHostConferenceRooms   OBJECT-TYPE
   SYNTAX      TruthValue
   MAX-ACCESS  read-only
   STATUS      current
   DESCRIPTION "Flag indicating whether the territory
                can host conference rooms."
   ::= { siteTopoTerritoryTableEntry 6 }


-- Site-to-Site Exclusions

siteTopoSiteToSiteExclusionCount  OBJECT-TYPE
   SYNTAX      Integer32
   MAX-ACCESS  read-only
   STATUS      current
   DESCRIPTION "Number of site-to-site exclusions configured in CMA system."
   ::= { cmaConfigSiteTopology 11 }

SiteTopoSiteToSiteExclusionTableEntry   ::= SEQUENCE
{
   siteToSiteExclusionIndex               CmaDefaultTableIndexRange,
   siteToSiteExclusionSiteA               OCTET STRING,
   siteToSiteExclusionSiteB               OCTET STRING
}

siteTopoSiteToSiteExclusionTable OBJECT-TYPE
   SYNTAX        SEQUENCE OF SiteTopoSiteToSiteExclusionTableEntry
   MAX-ACCESS    not-accessible
   STATUS        current
   DESCRIPTION   "Site topology site-to-site exclusion table. Lists the site-to-site exclusions  
                  defined in the system and their parameters."
   ::= { cmaConfigSiteTopology 12 }

siteTopoSiteToSiteExclusionTableEntry OBJECT-TYPE
   SYNTAX        SiteTopoSiteToSiteExclusionTableEntry
   MAX-ACCESS    not-accessible
   STATUS        current
   DESCRIPTION   "Site-to-site table entry."
   INDEX         { siteToSiteExclusionIndex }
   ::= { siteTopoSiteToSiteExclusionTable 1 }

siteToSiteExclusionIndex OBJECT-TYPE
   SYNTAX      CmaDefaultTableIndexRange
   MAX-ACCESS  read-only
   STATUS      current
   DESCRIPTION "Unique system-assigned ID for this entry." 
   ::= { siteTopoSiteToSiteExclusionTableEntry 1 }

siteToSiteExclusionSiteA        OBJECT-TYPE
   SYNTAX        OCTET STRING (SIZE(1..255))
   MAX-ACCESS    read-only
   STATUS        current
   DESCRIPTION   "Site A for the site-to-site exclusion."
   ::= { siteTopoSiteToSiteExclusionTableEntry 2 }

siteToSiteExclusionSiteB        OBJECT-TYPE
   SYNTAX        OCTET STRING (SIZE(1..255))
   MAX-ACCESS    read-only
   STATUS        current
   DESCRIPTION   "Site B for the site-to-site exclusion."
   ::= { siteTopoSiteToSiteExclusionTableEntry 3 }



-- Site Provisioning
sitetopologySiteProvisioningCount  OBJECT-TYPE
   SYNTAX      Integer32
   MAX-ACCESS  read-only
   STATUS      current
   DESCRIPTION "Number of site provisioing profiles configured in CMA system."
   ::= { cmaConfigSiteProvisioning 1 }

SiteTopologySiteProvisioningDetailsTableEntry   ::= SEQUENCE
{
   siteProvisioningSiteName                     OCTET STRING,
   siteCountry                                  OCTET STRING,
   siteDateFormat                               SiteProvisioningDateFormatType,
   siteAutoAdjustDst                            TruthValue,
   siteTimeFormat                               SiteProvisioningTimeFormatType,
   siteTimeServerUpdateType                     SiteTimeServerUpdateType,
   sitePrimaryTimeServerInetAddressType         InetAddressType,
   sitePrimaryTimeServerInetAddress             InetAddress,
   siteSecondaryTimeServerInetAddressType       InetAddressType,
   siteSecondaryTimeServerInetAddress           InetAddress,
   siteTimeZone                                 CmaTimeZone,
   siteFirewallUseFixedPorts                    TruthValue,
   siteFirewallTcpStartPort                     InetPortNumber,
   siteFirewallUdpStartPort                     InetPortNumber,
   siteFirewallH460Traversal                    TruthValue,
   siteFirewallNatConfiguration                 SiteNatConfigurationType,
   siteFirewallNatWanAddressType                InetAddressType,
   siteFirewallNatWanAddress                    InetAddress,
   siteFirewallNatH323Compatible                TruthValue,
   siteFirewallShowEpInGab                      TruthValue,
   siteFirewallEnableSipKeepAlives              TruthValue,
   siteH323EnableIpCalls                        TruthValue,
   siteH323GatekeeperIPAddressType              InetAddressType,
   siteH323GatekeeperIPAddress                  InetAddress,
   siteH3232UseGkForMultipointCalls             SiteUseGkForMultipointCallsType,
   siteProvisioningPollingInterval              Integer32,
   siteSoftupdatePollingInterval                Integer32,
   siteQosVideoTosValue                         Integer32,
   siteQosAudioTosValue                         Integer32,
   siteQosFeccTosValue                          Integer32,
   siteQosTosType                               SiteQosTypeOfServiceType,
   siteQosMaxMtuSize                            SiteQosMtuSizeType,
   siteQosEnablePvec                            TruthValue,
   siteQosEnableRsvp                            TruthValue,
   siteQosDynamicBandwidth                      TruthValue,
   siteQosMaxTransmitBandwidth                  SiteQosBandwidthType,
   siteQosMaxReceiveBandwidth                   SiteQosBandwidthType,
   siteSecurityUsePwdForRemoteAccess            TruthValue,
   siteSecurityEnableSecureMode                 TruthValue,
   siteSecurityEnableEncryption                 SiteSecurityEnableEncryptionType,
   siteSecurityEnableWebAccess                  TruthValue,
   siteSecurityEnableTelnetAccess               TruthValue,
   siteSecurityEnableSnmpAccess                 TruthValue,
   siteSecurityWebAccessPort                    InetPortNumber,
   siteSecurityAllowWebVideoDisplay             TruthValue,
   siteSecurityNtlmVersion                      OCTET STRING,
   siteCmadHeartbeatPollingInterval             Integer32,
   siteCmadInCallStatsPollingInterval           Integer32,
   siteCalendaringExchangeServerIPAddressType   InetAddressType,
   siteCalendaringExchangeServerIPAddress       InetAddress,
   siteSIPEnable                                TruthValue,
   siteSIPDomain                                OCTET STRING,
   siteSIPAutoDiscoverServer                    TruthValue,
   siteSIPProxyServerInetAddressType            InetAddressType,
   siteSIPProxyServerInetAddress                InetAddress,
   siteSIPRegistrarServerInetAddressType        InetAddressType,
   siteSIPRegistrarServerInetAddress            InetAddress,
   siteSIPBackupProxyServerInetAddressType      InetAddressType,
   siteSIPBackupProxyServerInetAddress          InetAddress,
   siteSIPBackupRegistrarServerInetAddressType  InetAddressType,
   siteSIPBackupRegistrarServerInetAddress      InetAddress,
   siteSIPTransportLayerProtocol                SiteSIPTransportProtocolType,
   siteSIPServerType                            SiteSIPServerType,
   siteSIPVerifyCertificate                     TruthValue,
   siteSIPUseEnterpriseCredentials              TruthValue,
   siteSecurityProfile                          OCTET STRING,
   siteSecurityIdleSessionTimeout               Integer32,
   siteSecurityFailedLoginThreshold             Integer32,
   siteSecurityFailedLoginWindow                Integer32,
   siteSecurityPortLockoutDuration              Integer32,
   siteSecurityMaxCertificateVerificationDepth  Integer32,
   siteSecurityVerifyCertforWebAccess           TruthValue,
   siteWhitelistIPEnable                        TruthValue,
--  siteEnableEnterpriseDir                      TruthValue,
   siteEnterpriseDirAdminGroup                  OCTET STRING,
   siteEnterpriseDirUserGroup                   OCTET STRING,
   siteDirectorySettingsUseThisServer           TruthValue,
   siteDirectorySettingsServerIPAddress         InetAddress,
   siteDirectorySettingsVerifyCertificate       TruthValue,
   sitePresenceSettingsUseThisServer            TruthValue,
   sitePresenceSettingsServerIPAddress          InetAddress,
   sitePresenceSettingsVerifyCertificate        TruthValue
}

sitetopologySiteProvisioningTable OBJECT-TYPE
   SYNTAX        SEQUENCE OF SiteTopologySiteProvisioningDetailsTableEntry
   MAX-ACCESS    not-accessible
   STATUS        current
   DESCRIPTION   "Site topology site provisioning details table. 
                  Contains the provisioning details for each site."
   ::= { cmaConfigSiteProvisioning 2 }

siteTopologySiteProvisioningDetailsTableEntry OBJECT-TYPE
   SYNTAX        SiteTopologySiteProvisioningDetailsTableEntry
   MAX-ACCESS    not-accessible
   STATUS        current
   DESCRIPTION   "Site provisioning details entry."
   INDEX         { siteIndex }
   ::= { sitetopologySiteProvisioningTable 1 }

siteProvisioningSiteName OBJECT-TYPE
   SYNTAX      OCTET STRING (SIZE(1..255)) 
   MAX-ACCESS  read-only
   STATUS      current
   DESCRIPTION "Name of the site."
   ::= { siteTopologySiteProvisioningDetailsTableEntry 1 }

siteCountry    OBJECT-TYPE
   SYNTAX      OCTET STRING
   MAX-ACCESS  read-only
   STATUS      current
   DESCRIPTION "Country of the site."
   ::= { siteTopologySiteProvisioningDetailsTableEntry 2 }

siteDateFormat   OBJECT-TYPE
   SYNTAX      SiteProvisioningDateFormatType
   MAX-ACCESS  read-only
   STATUS      current
   DESCRIPTION "Date format for the site."
   ::= { siteTopologySiteProvisioningDetailsTableEntry 3 }

siteAutoAdjustDst   OBJECT-TYPE
   SYNTAX      TruthValue
   MAX-ACCESS  read-only
   STATUS      current
   DESCRIPTION "Flag indicating whether to adjust the site's endpoint system clocks 
                for daylight saving time."
   ::= { siteTopologySiteProvisioningDetailsTableEntry 4 }

siteTimeFormat   OBJECT-TYPE
   SYNTAX      SiteProvisioningTimeFormatType
   MAX-ACCESS  read-only
   STATUS      current
   DESCRIPTION "Time format for the site."
   ::= { siteTopologySiteProvisioningDetailsTableEntry 5 }

siteTimeServerUpdateType   OBJECT-TYPE
   SYNTAX      SiteTimeServerUpdateType
   MAX-ACCESS  read-only
   STATUS      current
   DESCRIPTION "Time format for the site."
   ::= { siteTopologySiteProvisioningDetailsTableEntry 6 }

sitePrimaryTimeServerInetAddressType   OBJECT-TYPE
   SYNTAX      InetAddressType
   MAX-ACCESS  read-only
   STATUS      current
   DESCRIPTION "IP address type of the primary time server for the site."
   ::= { siteTopologySiteProvisioningDetailsTableEntry 7 }

sitePrimaryTimeServerInetAddress   OBJECT-TYPE
   SYNTAX      InetAddress
   MAX-ACCESS  read-only
   STATUS      current
   DESCRIPTION "IP address of the primary time server for the site."
   ::= { siteTopologySiteProvisioningDetailsTableEntry 8 }

siteSecondaryTimeServerInetAddressType   OBJECT-TYPE
   SYNTAX      InetAddressType
   MAX-ACCESS  read-only
   STATUS      current
   DESCRIPTION "IP address type of the secondary time server for the site."
   ::= { siteTopologySiteProvisioningDetailsTableEntry 9 }

siteSecondaryTimeServerInetAddress   OBJECT-TYPE
   SYNTAX      InetAddress
   MAX-ACCESS  read-only
   STATUS      current
   DESCRIPTION "IP address of the secondary time server for the site."
   ::= { siteTopologySiteProvisioningDetailsTableEntry 10 }

siteTimeZone   OBJECT-TYPE
   SYNTAX      CmaTimeZone 
   MAX-ACCESS  read-only
   STATUS      current
   DESCRIPTION "Time zone for the site."
   ::= { siteTopologySiteProvisioningDetailsTableEntry 11 }

siteFirewallUseFixedPorts   OBJECT-TYPE
   SYNTAX      TruthValue
   MAX-ACCESS  read-only
   STATUS      current
   DESCRIPTION "Flag indicating whether the TCP and UDP ports to use are defined
                for the site."
   ::= { siteTopologySiteProvisioningDetailsTableEntry 12 }

siteFirewallTcpStartPort   OBJECT-TYPE
   SYNTAX      InetPortNumber
   MAX-ACCESS  read-only
   STATUS      current
   DESCRIPTION "Starting TCP port number used by the site's endpoint systems."
   ::= { siteTopologySiteProvisioningDetailsTableEntry 13 }

siteFirewallUdpStartPort   OBJECT-TYPE
   SYNTAX      InetPortNumber
   MAX-ACCESS  read-only
   STATUS      current
   DESCRIPTION "Starting UDP port number used by the site's endpoint systems."
   ::= { siteTopologySiteProvisioningDetailsTableEntry 14 }

siteFirewallH460Traversal   OBJECT-TYPE
   SYNTAX      TruthValue
   MAX-ACCESS  read-only
   STATUS      current
   DESCRIPTION "Flag indicating whether the site's endpoint systems are  
                allowed to use H.460-based firewall traversal."
   ::= { siteTopologySiteProvisioningDetailsTableEntry 15 }

siteFirewallNatConfiguration   OBJECT-TYPE
   SYNTAX      SiteNatConfigurationType
   MAX-ACCESS  read-only
   STATUS      current
   DESCRIPTION "Flag indicating whether the site's endpoint systems should 
                determine the NAT public (WAN) address automatically."
   ::= { siteTopologySiteProvisioningDetailsTableEntry 16 }

siteFirewallNatWanAddressType   OBJECT-TYPE
   SYNTAX      InetAddressType
   MAX-ACCESS  read-only
   STATUS      current
   DESCRIPTION "Address type of the NAT public (WAN) IP address
                for the site. Only valid if the siteFirewallNatConfiguration
                attribute is set to manual."
   ::= { siteTopologySiteProvisioningDetailsTableEntry 17 }

siteFirewallNatWanAddress   OBJECT-TYPE
   SYNTAX      InetAddress
   MAX-ACCESS  read-only
   STATUS      current
   DESCRIPTION "NAT public (WAN) IP address for the site. 
                Only valid if the siteFirewallNatConfiguration
                attribute is set to manual."
   ::= { siteTopologySiteProvisioningDetailsTableEntry 18 }

siteFirewallNatH323Compatible   OBJECT-TYPE
   SYNTAX      TruthValue
   MAX-ACCESS  read-only
   STATUS      current
   DESCRIPTION "Flag indicating whether the site's endpoint systems are behind a NAT 
                capable of translating H.323 traffic."
   ::= { siteTopologySiteProvisioningDetailsTableEntry 19 }

siteFirewallShowEpInGab   OBJECT-TYPE
   SYNTAX      TruthValue
   MAX-ACCESS  read-only
   STATUS      current
   DESCRIPTION "Flag indicating whether endpoint system information is to be included
                in the global directory for the site."
   ::= { siteTopologySiteProvisioningDetailsTableEntry 20 }

siteFirewallEnableSipKeepAlives   OBJECT-TYPE
   SYNTAX      TruthValue
   MAX-ACCESS  read-only
   STATUS      current
   DESCRIPTION "Flag indicating whether SIP Keep Alives will be enabled for the site"
   ::= { siteTopologySiteProvisioningDetailsTableEntry 21 }

siteH323EnableIpCalls   OBJECT-TYPE
   SYNTAX      TruthValue
   MAX-ACCESS  read-only
   STATUS      current
   DESCRIPTION "Flag indicating whether IP H.323 calls are enabled for the site."
   ::= { siteTopologySiteProvisioningDetailsTableEntry 22 }

siteH323GatekeeperIPAddressType   OBJECT-TYPE
   SYNTAX      InetAddressType
   MAX-ACCESS  read-only
   STATUS      current
   DESCRIPTION "IP address type of the gatekeeper for the site.
                Only valid if the siteH323EnableIpCalls attribute is true."
   ::= { siteTopologySiteProvisioningDetailsTableEntry 24 }

siteH323GatekeeperIPAddress   OBJECT-TYPE
   SYNTAX      InetAddress
   MAX-ACCESS  read-only
   STATUS      current
   DESCRIPTION "IP address of the gatekeeper for the site.
                Only valid if the siteH323EnableIpCalls attribute is true."
   ::= { siteTopologySiteProvisioningDetailsTableEntry 25 }

siteH3232UseGkForMultipointCalls   OBJECT-TYPE
   SYNTAX      SiteUseGkForMultipointCallsType
   MAX-ACCESS  read-only
   STATUS      current
   DESCRIPTION "Flag indicating whether the site's multipoint calls use the endpoint system's
                internal multipoint capability or the Polycom MCUs' conference on demand feature."
   ::= { siteTopologySiteProvisioningDetailsTableEntry 26 }

siteProvisioningPollingInterval   OBJECT-TYPE
   SYNTAX      Integer32
   MAX-ACCESS  read-only
   STATUS      current
   DESCRIPTION "Frequency in minutes at which the site's endpoint systems poll the CMA
                for new provisioning information."
   ::= { siteTopologySiteProvisioningDetailsTableEntry 27 }

siteSoftupdatePollingInterval   OBJECT-TYPE
   SYNTAX      Integer32
   MAX-ACCESS  read-only
   STATUS      current
   DESCRIPTION "Frequency in minutes at which the site's endpoint systems poll the CMA
                for a new softupdate package."
   ::= { siteTopologySiteProvisioningDetailsTableEntry 28 }

siteQosVideoTosValue   OBJECT-TYPE
   SYNTAX      Integer32
   MAX-ACCESS  read-only
   STATUS      current
   DESCRIPTION "IP precedence or Diffserv value for the site's video packets."
   ::= { siteTopologySiteProvisioningDetailsTableEntry 29 }

siteQosAudioTosValue   OBJECT-TYPE
   SYNTAX      Integer32
   MAX-ACCESS  read-only
   STATUS      current
   DESCRIPTION "IP precedence or Diffserv value for the site's audio packets."
   ::= { siteTopologySiteProvisioningDetailsTableEntry 30 }

siteQosFeccTosValue   OBJECT-TYPE
   SYNTAX      Integer32
   MAX-ACCESS  read-only
   STATUS      current
   DESCRIPTION "IP precedence or Diffserv value for the site's Far End
                Camera Control packets."
   ::= { siteTopologySiteProvisioningDetailsTableEntry 31 }

siteQosTosType   OBJECT-TYPE
   SYNTAX      SiteQosTypeOfServiceType
   MAX-ACCESS  read-only
   STATUS      current
   DESCRIPTION "Type of service (IP precedence or Diffserv) for the site's 
                audio, video, and FECC TOS values."
   ::= { siteTopologySiteProvisioningDetailsTableEntry 32 }

siteQosMaxMtuSize   OBJECT-TYPE
   SYNTAX      SiteQosMtuSizeType
   MAX-ACCESS  read-only
   STATUS      current
   DESCRIPTION "Maximum transmission unit (MTU) size in bytes used in IP calls
                for the site."
   ::= { siteTopologySiteProvisioningDetailsTableEntry 33 }

siteQosEnablePvec   OBJECT-TYPE
   SYNTAX      TruthValue
   MAX-ACCESS  read-only
   STATUS      current
   DESCRIPTION "Flag indicating whether the site's endpoint systems can 
                use Polycom Video Error Concealment (PVEC) if packet loss occurs."
   ::= { siteTopologySiteProvisioningDetailsTableEntry 34 }

siteQosEnableRsvp   OBJECT-TYPE
   SYNTAX      TruthValue
   MAX-ACCESS  read-only
   STATUS      current
   DESCRIPTION "Flag indicating whether the site's endpoint systems can 
                use Resource Reservation Setup Protocol (RSVP) to request that 
                routers reserve bandwidth along an IP connection path."
   ::= { siteTopologySiteProvisioningDetailsTableEntry 35 }

siteQosDynamicBandwidth   OBJECT-TYPE
   SYNTAX      TruthValue
   MAX-ACCESS  read-only
   STATUS      current
   DESCRIPTION "Flag indicating whether the site's endpoint systems automatically 
                find the optimum line speed for a call."
   ::= { siteTopologySiteProvisioningDetailsTableEntry 36 }

siteQosMaxTransmitBandwidth   OBJECT-TYPE
   SYNTAX      SiteQosBandwidthType
   MAX-ACCESS  read-only
   STATUS      current
   DESCRIPTION "Maximum transmission line speed for the site in Kbps."
   ::= { siteTopologySiteProvisioningDetailsTableEntry 37 }

siteQosMaxReceiveBandwidth   OBJECT-TYPE
   SYNTAX      SiteQosBandwidthType
   MAX-ACCESS  read-only
   STATUS      current
   DESCRIPTION "Maximum reception line speed for the site in Kbps."
   ::= { siteTopologySiteProvisioningDetailsTableEntry 38 }

siteSecurityUsePwdForRemoteAccess   OBJECT-TYPE
   SYNTAX      TruthValue
   MAX-ACCESS  read-only
   STATUS      current
   DESCRIPTION "Flag indicating whether the local endpoint system password and remote access
                password are the same for the site."
   ::= { siteTopologySiteProvisioningDetailsTableEntry 39 }

siteSecurityEnableSecureMode   OBJECT-TYPE
   SYNTAX      TruthValue
   MAX-ACCESS  read-only
   STATUS      current
   DESCRIPTION "Flag indicating whether to operate in secure mode with  
                the site's devices."
   ::= { siteTopologySiteProvisioningDetailsTableEntry 40 }

siteSecurityEnableEncryption   OBJECT-TYPE
   SYNTAX      SiteSecurityEnableEncryptionType 
   MAX-ACCESS  read-only
   STATUS      current
   DESCRIPTION "Encryption usage setting for the site."
   ::= { siteTopologySiteProvisioningDetailsTableEntry 41 }

siteSecurityEnableWebAccess   OBJECT-TYPE
   SYNTAX      TruthValue 
   MAX-ACCESS  read-only
   STATUS      current
   DESCRIPTION "Flag indicating whether to allow web access to the site's 
                endpoint systems."
   ::= { siteTopologySiteProvisioningDetailsTableEntry 42 }

siteSecurityEnableTelnetAccess   OBJECT-TYPE
   SYNTAX      TruthValue 
   MAX-ACCESS  read-only
   STATUS      current
   DESCRIPTION "Flag indicating whether to allow telnet access to the site's 
                endpoint systems."
   ::= { siteTopologySiteProvisioningDetailsTableEntry 43 }

siteSecurityEnableSnmpAccess   OBJECT-TYPE
   SYNTAX      TruthValue 
   MAX-ACCESS  read-only
   STATUS      current
   DESCRIPTION "Flag indicating whether to allow SNMP access to the site's 
                endpoint systems."
   ::= { siteTopologySiteProvisioningDetailsTableEntry 44 }

siteSecurityWebAccessPort   OBJECT-TYPE
   SYNTAX      InetPortNumber
   MAX-ACCESS  read-only
   STATUS      current
   DESCRIPTION "Port number to use when accessing an endpoint system's web
                interface."
   ::= { siteTopologySiteProvisioningDetailsTableEntry 45 }

siteSecurityAllowWebVideoDisplay   OBJECT-TYPE
   SYNTAX      TruthValue 
   MAX-ACCESS  read-only
   STATUS      current
   DESCRIPTION "Flag indicating whether to allow viewing of the endpoint video
                using the endpoint system's web interface."
   ::= { siteTopologySiteProvisioningDetailsTableEntry 46 }

siteSecurityNtlmVersion    OBJECT-TYPE
   SYNTAX      OCTET STRING
   MAX-ACCESS  read-only
   STATUS      current
   DESCRIPTION "NTLM version setting for the site."
   ::= { siteTopologySiteProvisioningDetailsTableEntry 47 }

siteCmadHeartbeatPollingInterval   OBJECT-TYPE
   SYNTAX      Integer32
   MAX-ACCESS  read-only
   STATUS      current
   DESCRIPTION "Frequency in minutes at which the site's endpoint systems poll
                the CMA system for a heartbeat."
   ::= { siteTopologySiteProvisioningDetailsTableEntry 48 }

siteCmadInCallStatsPollingInterval   OBJECT-TYPE
   SYNTAX      Integer32
   MAX-ACCESS  read-only
   STATUS      current
   DESCRIPTION "Frequency in minutes at which the site's endpoint systems poll 
                the CMA system for in-call statistics."
   ::= { siteTopologySiteProvisioningDetailsTableEntry 49 }

siteCalendaringExchangeServerIPAddressType   OBJECT-TYPE
   SYNTAX      InetAddressType
   MAX-ACCESS  read-only
   STATUS      current
   DESCRIPTION "IP address type of the Exchange server for the site."
   ::= { siteTopologySiteProvisioningDetailsTableEntry 50 }

siteCalendaringExchangeServerIPAddress   OBJECT-TYPE
   SYNTAX      InetAddress
   MAX-ACCESS  read-only
   STATUS      current
   DESCRIPTION "IP address of the Exchange server for the site."
   ::= { siteTopologySiteProvisioningDetailsTableEntry 51 }

--------------------------------------------------------------------------------
siteSIPEnable   OBJECT-TYPE
   SYNTAX      TruthValue 
   MAX-ACCESS  read-only
   STATUS      current
   DESCRIPTION "Flag indicating whether SIP is
                Enabled or."
   ::= { siteTopologySiteProvisioningDetailsTableEntry 52 }

siteSIPDomain   OBJECT-TYPE
   SYNTAX      OCTET STRING (SIZE(1..255))
   MAX-ACCESS  read-only
   STATUS      current
   DESCRIPTION "Name of the SIP Domain."
   ::= { siteTopologySiteProvisioningDetailsTableEntry 53 }

siteSIPAutoDiscoverServer   OBJECT-TYPE
   SYNTAX      TruthValue 
   MAX-ACCESS  read-only
   STATUS      current
   DESCRIPTION "Flag indicating whether autodiscovering SIP Server
                is Enabled."
   ::= { siteTopologySiteProvisioningDetailsTableEntry 54 }

siteSIPProxyServerInetAddressType   OBJECT-TYPE
   SYNTAX      InetAddressType
   MAX-ACCESS  read-only
   STATUS      current
   DESCRIPTION "IP address type for the SIP Proxy Server."
   DEFVAL      { ipv4 }
   ::= { siteTopologySiteProvisioningDetailsTableEntry 55 }

siteSIPProxyServerInetAddress   OBJECT-TYPE
   SYNTAX      InetAddress
   MAX-ACCESS  read-only
   STATUS      current
   DESCRIPTION "IP address for the SIP Proxy Server."
   DEFVAL      { "" }
   ::= { siteTopologySiteProvisioningDetailsTableEntry 56 }

siteSIPRegistrarServerInetAddressType   OBJECT-TYPE
   SYNTAX      InetAddressType
   MAX-ACCESS  read-only
   STATUS      current
   DESCRIPTION "IP address type for the SIP Registrar Server."
   DEFVAL      { ipv4 }
   ::= { siteTopologySiteProvisioningDetailsTableEntry 57 }

siteSIPRegistrarServerInetAddress   OBJECT-TYPE
   SYNTAX      InetAddress
   MAX-ACCESS  read-only
   STATUS      current
   DESCRIPTION "IP address for the SIP Registrar Server."
   DEFVAL      { "" }
   ::= { siteTopologySiteProvisioningDetailsTableEntry 58 }

siteSIPBackupProxyServerInetAddressType   OBJECT-TYPE
   SYNTAX      InetAddressType
   MAX-ACCESS  read-only
   STATUS      current
   DESCRIPTION "IP address type for the SIPBackup Proxy Server."
   DEFVAL      { ipv4 }
   ::= { siteTopologySiteProvisioningDetailsTableEntry 59 }

siteSIPBackupProxyServerInetAddress   OBJECT-TYPE
   SYNTAX      InetAddress
   MAX-ACCESS  read-only
   STATUS      current
   DESCRIPTION "IP address for the SIPBackupProxyServer."
   DEFVAL      { "" }
   ::= { siteTopologySiteProvisioningDetailsTableEntry 60 }

siteSIPBackupRegistrarServerInetAddressType   OBJECT-TYPE
   SYNTAX      InetAddressType
   MAX-ACCESS  read-only
   STATUS      current
   DESCRIPTION "IP address type for the SIPBackupregistrarServer."
   DEFVAL      { ipv4 }
   ::= { siteTopologySiteProvisioningDetailsTableEntry 61 }

siteSIPBackupRegistrarServerInetAddress   OBJECT-TYPE
   SYNTAX      InetAddress
   MAX-ACCESS  read-only
   STATUS      current
   DESCRIPTION "IP address for the SIPBackupregistrarServer."
   DEFVAL      { "" }
   ::= { siteTopologySiteProvisioningDetailsTableEntry 62 }

siteSIPTransportLayerProtocol   OBJECT-TYPE
   SYNTAX      SiteSIPTransportProtocolType
   MAX-ACCESS  read-only
   STATUS      current
   DESCRIPTION "Transport Layer Protocol for the SIP."
   ::= { siteTopologySiteProvisioningDetailsTableEntry 63 }

siteSIPServerType   OBJECT-TYPE
   SYNTAX      SiteSIPServerType
   MAX-ACCESS  read-only
   STATUS      current
   DESCRIPTION "SIP Server type for SIP Protocol ."
   ::= { siteTopologySiteProvisioningDetailsTableEntry 64 }

siteSIPVerifyCertificate   OBJECT-TYPE
   SYNTAX      TruthValue 
   MAX-ACCESS  read-only
   STATUS      current
   DESCRIPTION "Flag indicating if the certificates are verified."
   ::= { siteTopologySiteProvisioningDetailsTableEntry 65 }

siteSIPUseEnterpriseCredentials  OBJECT-TYPE
   SYNTAX      TruthValue 
   MAX-ACCESS  read-only
   STATUS      current
   DESCRIPTION "Flag indicating whether Enterprise Directory Credentials 
                are used for login."
   ::= { siteTopologySiteProvisioningDetailsTableEntry 66 }
---------------------------------------------------------------------------------------------------------------------------
siteSecurityProfile   OBJECT-TYPE
   SYNTAX      OCTET STRING (SIZE(1..255))
   MAX-ACCESS  read-only
   STATUS      current
   DESCRIPTION "Security Profile Selected for this site ."
   ::= { siteTopologySiteProvisioningDetailsTableEntry 67 }

siteSecurityIdleSessionTimeout   OBJECT-TYPE
   SYNTAX      Integer32
   MAX-ACCESS  read-only
   STATUS      current
   DESCRIPTION "Idle session Timeout in Minutes."
   ::= { siteTopologySiteProvisioningDetailsTableEntry 68 }

siteSecurityFailedLoginThreshold   OBJECT-TYPE
   SYNTAX      Integer32
   MAX-ACCESS  read-only
   STATUS      current
   DESCRIPTION "Lock Port after Failed Logins, zero is off"
   ::= { siteTopologySiteProvisioningDetailsTableEntry 69 }

siteSecurityFailedLoginWindow   OBJECT-TYPE
   SYNTAX      Integer32
   MAX-ACCESS  read-only
   STATUS      current
   DESCRIPTION "Failed Login Window in hours."
   ::= { siteTopologySiteProvisioningDetailsTableEntry 71 }

siteSecurityPortLockoutDuration   OBJECT-TYPE
   SYNTAX      Integer32
   MAX-ACCESS  read-only
   STATUS      current
   DESCRIPTION "Port Lockout duration in minutes."
   ::= { siteTopologySiteProvisioningDetailsTableEntry 72 }

siteSecurityMaxCertificateVerificationDepth   OBJECT-TYPE
   SYNTAX      Integer32
   MAX-ACCESS  read-only
   STATUS      current
   DESCRIPTION "MAximum Peer Certificate Verification Depth."
   ::= { siteTopologySiteProvisioningDetailsTableEntry 73 }


siteSecurityVerifyCertforWebAccess  OBJECT-TYPE
   SYNTAX      TruthValue 
   MAX-ACCESS  read-only
   STATUS      current
   DESCRIPTION "Flag indicating whether certificates are to be verified for 
                all Web Accesses."
   ::= { siteTopologySiteProvisioningDetailsTableEntry 74 }

siteWhitelistIPEnable  OBJECT-TYPE
   SYNTAX      TruthValue 
   MAX-ACCESS  read-only
   STATUS      current
   DESCRIPTION "Flag indicating whether WhiteList for IP's is enabled."
   ::= { siteTopologySiteProvisioningDetailsTableEntry 75 }

siteEnterpriseDirAdminGroup OBJECT-TYPE
   SYNTAX      OCTET STRING (SIZE(1..255))
   MAX-ACCESS  read-only
   STATUS      current
   DESCRIPTION "Name of the Enterprise Directory Admin Group."
   ::= { siteTopologySiteProvisioningDetailsTableEntry 76}

siteEnterpriseDirUserGroup  OBJECT-TYPE
   SYNTAX      OCTET STRING (SIZE(1..255))
   MAX-ACCESS  read-only
   STATUS      current
   DESCRIPTION "Name of the Enterprise Directory User Group."
   ::= { siteTopologySiteProvisioningDetailsTableEntry 77 }

siteDirectorySettingsUseThisServer   OBJECT-TYPE
   SYNTAX      TruthValue 
   MAX-ACCESS  read-only
   STATUS      current
   DESCRIPTION "Flag indicating whether use this server for Directory server."
   ::= { siteTopologySiteProvisioningDetailsTableEntry 78 }

siteDirectorySettingsServerIPAddress   OBJECT-TYPE
   SYNTAX      InetAddress
   MAX-ACCESS  read-only
   STATUS      current
   DESCRIPTION "IP address of the Directory server for the site."
   ::= { siteTopologySiteProvisioningDetailsTableEntry 79 }

siteDirectorySettingsVerifyCertificate   OBJECT-TYPE
   SYNTAX      TruthValue 
   MAX-ACCESS  read-only
   STATUS      current
   DESCRIPTION "Flag indicating whether Verify Certificate is enabled for this site."
   ::= { siteTopologySiteProvisioningDetailsTableEntry 80 }

sitePresenceSettingsUseThisServer   OBJECT-TYPE
   SYNTAX      TruthValue 
   MAX-ACCESS  read-only
   STATUS      current
   DESCRIPTION "Flag indicating whether use this server for Presence server."
   ::= { siteTopologySiteProvisioningDetailsTableEntry 81 }

sitePresenceSettingsServerIPAddress   OBJECT-TYPE
   SYNTAX      InetAddress
   MAX-ACCESS  read-only
   STATUS      current
   DESCRIPTION "IP address of the Presence server for the site."
   ::= { siteTopologySiteProvisioningDetailsTableEntry 82 }

sitePresenceSettingsVerifyCertificate   OBJECT-TYPE
   SYNTAX      TruthValue 
   MAX-ACCESS  read-only
   STATUS      current
   DESCRIPTION "Flag indicating whether Verify Certificate is enabled for this site."
   ::= { siteTopologySiteProvisioningDetailsTableEntry 83 }



-- END Site topology

-- RPAD Site Provisioning BEGIN
sitetopologyRPADSiteProvisioningCount  OBJECT-TYPE
   SYNTAX      Integer32
   MAX-ACCESS  read-only
   STATUS      current
   DESCRIPTION "Number of RPAD site provisioing profiles configured in CMA system."
   ::= { cmaConfigSiteProvisioning 3 }


RPADSiteTopologySiteProvisioningDetailsTableEntry   ::= SEQUENCE
{
   rpadsiteProvisioningSiteName                     OCTET STRING,    
   rpadsiteTimeServerUpdateType                     SiteTimeServerUpdateType,
   rpadsitePrimaryTimeServerInetAddressType         InetAddressType,
   rpadsitePrimaryTimeServerInetAddress             InetAddress,
   rpadsiteSecondaryTimeServerInetAddressType       InetAddressType,
   rpadsiteSecondaryTimeServerInetAddress           InetAddress,

   rpadsiteProvisioningPollingInterval              Integer32,
   rpadsiteCmadHeartbeatPollingInterval             Integer32,
   rpadserverStatusPollingInterval                  Integer32,

   rpadsiteH323EnableIpCalls                        TruthValue,
   rpadsiteH323GatekeeperIPAddressType              InetAddressType,
   rpadsiteH323GatekeeperIPAddress                  InetAddress,
 
   rpadsiteSIPEnable                                TruthValue,
   rpadsiteSIPProxyServerInetAddressType            InetAddressType,
   rpadsiteSIPProxyServerInetAddress                InetAddress,
   rpadsiteSIPRegistrarServerInetAddressType        InetAddressType,
   rpadsiteSIPRegistrarServerInetAddress            InetAddress,
   rpadsiteSIPTransportLayerProtocol                SiteSIPTransportProtocolType,
   rpadsiteSIPVerifyCertificate                     TruthValue,

   rpadsiteDirectorySettingsUseThisServer           TruthValue,
   rpadsiteDirectorySettingsServerIPAddress         InetAddress,
   rpadsiteDirectorySettingsVerifyCertificate       TruthValue,
   rpadsitePresenceSettingsUseThisServer            TruthValue,
   rpadsitePresenceSettingsServerIPAddress          InetAddress,
   rpadsitePresenceSettingsVerifyCertificate        TruthValue
}

sitetopologyRPADSiteProvisioningTable OBJECT-TYPE
   SYNTAX        SEQUENCE OF RPADSiteTopologySiteProvisioningDetailsTableEntry
   MAX-ACCESS    not-accessible
   STATUS        current
   DESCRIPTION   "Site topology RPAD site provisioning details table. 
                  Contains the provisioning details for each site."
   ::= { cmaConfigSiteProvisioning 4 }

rpadSiteTopologySiteProvisioningDetailsTableEntry OBJECT-TYPE
   SYNTAX        RPADSiteTopologySiteProvisioningDetailsTableEntry
   MAX-ACCESS    not-accessible
   STATUS        current
   DESCRIPTION   "RPAD Site provisioning details entry."
   INDEX         { siteIndex }
   ::= { sitetopologyRPADSiteProvisioningTable 1 }

rpadsiteProvisioningSiteName OBJECT-TYPE
   SYNTAX      OCTET STRING (SIZE(1..255)) 
   MAX-ACCESS  read-only
   STATUS      current
   DESCRIPTION "Name of the site."
   ::= { rpadSiteTopologySiteProvisioningDetailsTableEntry 1 }

rpadsiteTimeServerUpdateType   OBJECT-TYPE
   SYNTAX      SiteTimeServerUpdateType
   MAX-ACCESS  read-only
   STATUS      current
   DESCRIPTION "Time format for the rpad site."
   ::= { rpadSiteTopologySiteProvisioningDetailsTableEntry 2 }

rpadsitePrimaryTimeServerInetAddressType   OBJECT-TYPE
   SYNTAX      InetAddressType
   MAX-ACCESS  read-only
   STATUS      current
   DESCRIPTION "IP address type of the primary time server for the rpad site."
   ::= { rpadSiteTopologySiteProvisioningDetailsTableEntry 3 }

rpadsitePrimaryTimeServerInetAddress   OBJECT-TYPE
   SYNTAX      InetAddress
   MAX-ACCESS  read-only
   STATUS      current
   DESCRIPTION "IP address of the primary time server for the rpad site."
   ::= { rpadSiteTopologySiteProvisioningDetailsTableEntry 4 }

rpadsiteSecondaryTimeServerInetAddressType   OBJECT-TYPE
   SYNTAX      InetAddressType
   MAX-ACCESS  read-only
   STATUS      current
   DESCRIPTION "IP address type of the secondary time server for the rpad site."
   ::= { rpadSiteTopologySiteProvisioningDetailsTableEntry 5 }

rpadsiteSecondaryTimeServerInetAddress   OBJECT-TYPE
   SYNTAX      InetAddress
   MAX-ACCESS  read-only
   STATUS      current
   DESCRIPTION "IP address of the secondary time server for the rpad site."
   ::= { rpadSiteTopologySiteProvisioningDetailsTableEntry 6 }

rpadsiteProvisioningPollingInterval   OBJECT-TYPE
   SYNTAX      Integer32
   MAX-ACCESS  read-only
   STATUS      current
   DESCRIPTION "Frequency at which the site's endpoint systems poll the CMA
                for new provisioning information."
   ::= { rpadSiteTopologySiteProvisioningDetailsTableEntry 7}

rpadsiteCmadHeartbeatPollingInterval   OBJECT-TYPE
   SYNTAX      Integer32
   MAX-ACCESS  read-only
   STATUS      current
   DESCRIPTION "Frequency at which the site's endpoint systems poll the CMA 
                system for a heartbeat."
   ::= { rpadSiteTopologySiteProvisioningDetailsTableEntry 8 }

rpadserverStatusPollingInterval  OBJECT-TYPE
   SYNTAX      Integer32
   MAX-ACCESS  read-only
   STATUS      current
   DESCRIPTION "Frequency at which the site's endpoint systems poll the CMA 
                system for a server status"
   ::= { rpadSiteTopologySiteProvisioningDetailsTableEntry 9 }

rpadsiteH323EnableIpCalls   OBJECT-TYPE
   SYNTAX      TruthValue
   MAX-ACCESS  read-only
   STATUS      current
   DESCRIPTION "Flag indicating whether IP H.323 calls are enabled for the site."
   ::= { rpadSiteTopologySiteProvisioningDetailsTableEntry 10 }

rpadsiteH323GatekeeperIPAddressType   OBJECT-TYPE
   SYNTAX      InetAddressType
   MAX-ACCESS  read-only
   STATUS      current
   DESCRIPTION "IP address type of the gatekeeper for the site.
                Only valid if the siteH323EnableIpCalls attribute is true."
   ::= { rpadSiteTopologySiteProvisioningDetailsTableEntry 11 }

rpadsiteH323GatekeeperIPAddress   OBJECT-TYPE
   SYNTAX      InetAddress
   MAX-ACCESS  read-only
   STATUS      current
   DESCRIPTION "IP address of the gatekeeper for the site.
                Only valid if the siteH323EnableIpCalls attribute is true."
   ::= { rpadSiteTopologySiteProvisioningDetailsTableEntry 12 }

rpadsiteSIPEnable   OBJECT-TYPE
   SYNTAX      TruthValue 
   MAX-ACCESS  read-only
   STATUS      current
   DESCRIPTION "Flag indicating whether SIP is
                Enabled or."
   ::= { rpadSiteTopologySiteProvisioningDetailsTableEntry 13 }

rpadsiteSIPProxyServerInetAddressType   OBJECT-TYPE
   SYNTAX      InetAddressType
   MAX-ACCESS  read-only
   STATUS      current
   DESCRIPTION "IP address type for the SIP Proxy Server."
   DEFVAL      { ipv4 }
   ::= { rpadSiteTopologySiteProvisioningDetailsTableEntry 14 }

rpadsiteSIPProxyServerInetAddress   OBJECT-TYPE
   SYNTAX      InetAddress
   MAX-ACCESS  read-only
   STATUS      current
   DESCRIPTION "IP address for the SIP Proxy Server."
   DEFVAL      { "" }
   ::= { rpadSiteTopologySiteProvisioningDetailsTableEntry 15 }

rpadsiteSIPRegistrarServerInetAddressType   OBJECT-TYPE
   SYNTAX      InetAddressType
   MAX-ACCESS  read-only
   STATUS      current
   DESCRIPTION "IP address type for the SIP Registrar Server."
   DEFVAL      { ipv4 }
   ::= { rpadSiteTopologySiteProvisioningDetailsTableEntry 16 }

rpadsiteSIPRegistrarServerInetAddress   OBJECT-TYPE
   SYNTAX      InetAddress
   MAX-ACCESS  read-only
   STATUS      current
   DESCRIPTION "IP address for the SIP Registrar Server."
   DEFVAL      { "" }
   ::= { rpadSiteTopologySiteProvisioningDetailsTableEntry 17 }

rpadsiteSIPTransportLayerProtocol   OBJECT-TYPE
   SYNTAX      SiteSIPTransportProtocolType
   MAX-ACCESS  read-only
   STATUS      current
   DESCRIPTION "Transport Layer Protocol for the SIP."
   ::= { rpadSiteTopologySiteProvisioningDetailsTableEntry 18 }

rpadsiteSIPVerifyCertificate   OBJECT-TYPE
   SYNTAX      TruthValue 
   MAX-ACCESS  read-only
   STATUS      current
   DESCRIPTION "Flag indicating if the certificates are verified."
   ::= { rpadSiteTopologySiteProvisioningDetailsTableEntry 19 }

rpadsiteDirectorySettingsUseThisServer   OBJECT-TYPE
   SYNTAX      TruthValue 
   MAX-ACCESS  read-only
   STATUS      current
   DESCRIPTION "Flag indicating whether use this server for Directory server."
   ::= { rpadSiteTopologySiteProvisioningDetailsTableEntry 20 }

rpadsiteDirectorySettingsServerIPAddress   OBJECT-TYPE
   SYNTAX      InetAddress
   MAX-ACCESS  read-only
   STATUS      current
   DESCRIPTION "IP address of the Directory server for the site."
   ::= { rpadSiteTopologySiteProvisioningDetailsTableEntry 21 }

rpadsiteDirectorySettingsVerifyCertificate   OBJECT-TYPE
   SYNTAX      TruthValue 
   MAX-ACCESS  read-only
   STATUS      current
   DESCRIPTION "Flag indicating whether Verify Certificate is enabled for this site."
   ::= { rpadSiteTopologySiteProvisioningDetailsTableEntry 22 }

rpadsitePresenceSettingsUseThisServer   OBJECT-TYPE
   SYNTAX      TruthValue 
   MAX-ACCESS  read-only
   STATUS      current
   DESCRIPTION "Flag indicating whether use this server for Presence server."
   ::= { rpadSiteTopologySiteProvisioningDetailsTableEntry 23 }

rpadsitePresenceSettingsServerIPAddress   OBJECT-TYPE
   SYNTAX      InetAddress
   MAX-ACCESS  read-only
   STATUS      current
   DESCRIPTION "IP address of the Presence server for the site."
   ::= { rpadSiteTopologySiteProvisioningDetailsTableEntry 24 }

rpadsitePresenceSettingsVerifyCertificate   OBJECT-TYPE
   SYNTAX      TruthValue 
   MAX-ACCESS  read-only
   STATUS      current
   DESCRIPTION "Flag indicating whether Verify Certificate is enabled for this site."
   ::= { rpadSiteTopologySiteProvisioningDetailsTableEntry 25 } 
-- RPAD Site Provisioning END



-- START conference settings configuration
cmaConferenceSettingGroup  OBJECT-GROUP
   OBJECTS
   {
      cmaConferenceConfigTimeWarning,
      cmaConferenceConfigIncludeScheduler,
      cmaConferenceConfigAllowOverbookForDial-in,
      cmaConferenceConfigPasscodeLength
      
   }
   STATUS current
   DESCRIPTION "CMA conference settings conformance group."
   ::= { cmaConfigConformance 16 }

cmaConferenceConfigTimeWarning OBJECT-TYPE
   SYNTAX        TruthValue
   MAX-ACCESS    read-only
   STATUS        current
   DESCRIPTION   "Flag indicating whether a message is sent to video endpoint systems
                  to let users know that the conference is ending soon." 
   ::= { cmaConfigConferenceGeneral 1 }

cmaConferenceConfigIncludeScheduler OBJECT-TYPE
   SYNTAX        TruthValue
   MAX-ACCESS    read-only
   STATUS        current
   DESCRIPTION   "Flag indicating whether the conference scheduler is automatically
                  added to a new conference."
   ::= { cmaConfigConferenceGeneral 2 }

cmaConferenceConfigAllowOverbookForDial-in OBJECT-TYPE
   SYNTAX        TruthValue
   MAX-ACCESS    read-only
   STATUS        current
   DESCRIPTION   "Flag indicating whether over-booking Dial-in Partipants is allowed
                  for a particular conference."
   ::= { cmaConfigConferenceGeneral 3 }

cmaConferenceConfigPasscodeLength   OBJECT-TYPE
   SYNTAX Integer32
   MAX-ACCESS read-only
   STATUS current
   DESCRIPTION "Conference and chairperson passcode length."
   ::= { cmaConfigConferenceGeneral 4 }

-- END conference settings configuration

-- START Room configuration

cmaConfigRoomGroup  OBJECT-GROUP
   OBJECTS
   {
      cmaConfigRoomCount,
      roomIndex,
      roomName,
      roomDescription, 
      roomSite,
      roomEmailAddress
   }
   STATUS current
   DESCRIPTION "CMA room configuration conformance group."
   ::= { cmaConfigConformance 18 }

cmaConfigRoomCount   OBJECT-TYPE
   SYNTAX Integer32
   MAX-ACCESS read-only
   STATUS current
   DESCRIPTION "Total number of configured rooms."
   ::= { cmaConfigRooms 1 }

CmaConfigRoomTableEntry  ::= SEQUENCE
{
   roomIndex          CmaDefaultTableIndexRange,
   roomName           OCTET STRING,
   roomDescription    OCTET STRING,
   roomSite           OCTET STRING,
   roomEmailAddress   OCTET STRING
}

cmaConfigRoomTable   OBJECT-TYPE
   SYNTAX        SEQUENCE OF CmaConfigRoomTableEntry
   MAX-ACCESS    not-accessible
   STATUS        current
   DESCRIPTION   "CMA room table. Contains information about the rooms 
                  defined in the system."
   ::= { cmaConfigRooms 2 }

cmaConfigRoomTableEntry OBJECT-TYPE
   SYNTAX        CmaConfigRoomTableEntry
   MAX-ACCESS    not-accessible
   STATUS        current
   DESCRIPTION   "Room configuration table entry."
   INDEX         { roomIndex }
   ::= { cmaConfigRoomTable 1 }

roomIndex OBJECT-TYPE
   SYNTAX      CmaDefaultTableIndexRange
   MAX-ACCESS  read-only
   STATUS      current
   DESCRIPTION "Unique system-assigned ID for this entry." 
   ::= { cmaConfigRoomTableEntry 1 }

roomName OBJECT-TYPE 
   SYNTAX      OCTET STRING (SIZE(0..255))
   MAX-ACCESS  read-only
   STATUS      current
   DESCRIPTION "Name of the room."
   ::= { cmaConfigRoomTableEntry 2 } 
 
roomDescription OBJECT-TYPE 
   SYNTAX      OCTET STRING (SIZE(0..255))
   MAX-ACCESS  read-only
   STATUS      current
   DESCRIPTION "Description of the room."
   ::= { cmaConfigRoomTableEntry 3 }

roomSite OBJECT-TYPE 
   SYNTAX      OCTET STRING (SIZE(0..255))
   MAX-ACCESS  read-only
   STATUS      current
   DESCRIPTION "Name of the site in which the room is located."
   ::= { cmaConfigRoomTableEntry 4 }

roomEmailAddress OBJECT-TYPE 
   SYNTAX      OCTET STRING (SIZE(0..255))
   MAX-ACCESS  read-only
   STATUS      current
   DESCRIPTION "Email address for the room."
   ::= { cmaConfigRoomTableEntry 5 }  
   
-- END Room configuration

-- START SNMP configuration
cmaConfigSnmpGroup   OBJECT-GROUP
   OBJECTS
   {
      snmpVersion,
      snmpTransport,
      snmpPort,
      snmpCommunity,
      snmpV3ContextName,
      snmpV3SecurityUser,
      snmpAuthenticationType,
      snmpEncryptionType,
      snmpV3LocalEngineId,
      recipientIndex,
      recipientIPAddressType,
      recipientIPAddress,
      recipientPort,
      recipientTransportType,
      recipientNotificationType,
      recipientSnmpVersion,
      recipientSecurityUser,
      recipientAuthenticationType,
      recipientEncryptionType
   }
   STATUS current
   DESCRIPTION "CMA SNMP configuration conformance group."
   ::= { cmaConfigConformance 22 }

snmpVersion OBJECT-TYPE   
   SYNTAX      SnmpVersionType
   MAX-ACCESS  read-only
   STATUS      current
   DESCRIPTION "SNMP version."
   ::= { cmaConfigSnmp 1 }

snmpTransport OBJECT-TYPE
   SYNTAX      SnmpTransportType
   MAX-ACCESS  read-only
   STATUS      current
   DESCRIPTION "Type of transport used for SNMP."
   ::= { cmaConfigSnmp 2 }

snmpPort OBJECT-TYPE
   SYNTAX      InetPortNumber
   MAX-ACCESS  read-only
   STATUS      current
   DESCRIPTION "Port used for SNMP."
   ::= { cmaConfigSnmp 3 }

snmpCommunity OBJECT-TYPE
   SYNTAX      OCTET STRING (SIZE(0..255))
   MAX-ACCESS  read-only
   STATUS      current
   DESCRIPTION "SNMP v2 community name."
   ::= { cmaConfigSnmp 4 }

snmpV3ContextName OBJECT-TYPE
   SYNTAX      OCTET STRING (SIZE(0..255))
   MAX-ACCESS  read-only
   STATUS      current
   DESCRIPTION "SNMP v3 context name."
   ::= { cmaConfigSnmp 5 }

snmpV3SecurityUser OBJECT-TYPE
   SYNTAX      OCTET STRING (SIZE(0..255))
   MAX-ACCESS  read-only
   STATUS      current
   DESCRIPTION "SNMP v3 security user name."
   ::= { cmaConfigSnmp 6 }

snmpAuthenticationType OBJECT-TYPE
   SYNTAX      SnmpAuthenticationType
   MAX-ACCESS  read-only
   STATUS      current
   DESCRIPTION "SNMP v3 authentication type."
   ::= { cmaConfigSnmp 7 }

snmpEncryptionType OBJECT-TYPE
   SYNTAX      SnmpEncryptionType
   MAX-ACCESS  read-only
   STATUS      current
   DESCRIPTION "SNMP v3 encryption type."
   ::= { cmaConfigSnmp 8 }

snmpV3LocalEngineId OBJECT-TYPE
   SYNTAX      OCTET STRING (SIZE(0..255))
   MAX-ACCESS  read-only
   STATUS      current
   DESCRIPTION "SNMP v3 local engine ID."
   ::= { cmaConfigSnmp 9 }

SnmpNoticationRecipientTableEntry  ::= SEQUENCE
{
   recipientIndex              CmaDefaultTableIndexRange,
   recipientIPAddressType      InetAddressType,
   recipientIPAddress          InetAddress,
   recipientPort               InetPortNumber,
   recipientTransportType      SnmpTransportType,
   recipientNotificationType   SnmpNotificationType,
   recipientSnmpVersion        SnmpVersionType,
   recipientSecurityUser       OCTET STRING,
   recipientAuthenticationType SnmpAuthenticationType,
   recipientEncryptionType     SnmpEncryptionType
}

snmpNotificationRecipientTable OBJECT-TYPE
   SYNTAX        SEQUENCE OF SnmpNoticationRecipientTableEntry
   MAX-ACCESS    not-accessible
   STATUS        current
   DESCRIPTION   "SNMP notification recipients table. Each entry contains the parameters for 
                  an agent that receives notifications from the CMA server."
   ::= { cmaConfigSnmp 10 }

snmpNoticationRecipientTableEntry OBJECT-TYPE
   SYNTAX        SnmpNoticationRecipientTableEntry
   MAX-ACCESS    not-accessible
   STATUS        current
   DESCRIPTION   "SNMP notification recipient table entry."
   INDEX         { recipientIndex }
   ::= { snmpNotificationRecipientTable 1 }

recipientIndex OBJECT-TYPE
   SYNTAX      CmaDefaultTableIndexRange
   MAX-ACCESS  read-only
   STATUS      current
   DESCRIPTION "Unique system-assigned ID for this entry." 
   ::= { snmpNoticationRecipientTableEntry 1 }

recipientIPAddressType OBJECT-TYPE
   SYNTAX      InetAddressType
   MAX-ACCESS  read-only
   STATUS      current
   DESCRIPTION "IP address type of the SNMP recipient."
   ::= { snmpNoticationRecipientTableEntry 2 }

recipientIPAddress OBJECT-TYPE
   SYNTAX      InetAddress
   MAX-ACCESS  read-only
   STATUS      current
   DESCRIPTION "IP address of the SNMP recipient."
   ::= { snmpNoticationRecipientTableEntry 3 }

recipientPort OBJECT-TYPE
   SYNTAX      InetPortNumber
   MAX-ACCESS  read-only
   STATUS      current
   DESCRIPTION "IP port number of the SNMP recipient."
   ::= { snmpNoticationRecipientTableEntry 4 }

recipientTransportType OBJECT-TYPE
   SYNTAX      SnmpTransportType
   MAX-ACCESS  read-only
   STATUS      current
   DESCRIPTION "Transport type for the SNMP recipient."
   ::= { snmpNoticationRecipientTableEntry 5 }

recipientNotificationType OBJECT-TYPE
   SYNTAX      SnmpNotificationType
   MAX-ACCESS  read-only
   STATUS      current
   DESCRIPTION "Notification type (trap or inform) for the SNMP recipient."
   ::= { snmpNoticationRecipientTableEntry 6 }

recipientSnmpVersion OBJECT-TYPE
   SYNTAX      SnmpVersionType
   MAX-ACCESS  read-only
   STATUS      current
   DESCRIPTION "SNMP version of notifications for the SNMP recipient."
   ::= { snmpNoticationRecipientTableEntry 7 }

recipientSecurityUser OBJECT-TYPE
   SYNTAX      OCTET STRING (SIZE(0..255))
   MAX-ACCESS  read-only
   STATUS      current
   DESCRIPTION "SNMP V3 security user name for the SNMP recipient."
   ::= { snmpNoticationRecipientTableEntry 8 }

recipientAuthenticationType OBJECT-TYPE
   SYNTAX      SnmpAuthenticationType
   MAX-ACCESS  read-only
   STATUS      current
   DESCRIPTION "SNMP V3 authentication type for the SNMP recipient."
   ::= { snmpNoticationRecipientTableEntry 9 }

recipientEncryptionType OBJECT-TYPE
   SYNTAX      SnmpEncryptionType
   MAX-ACCESS  read-only
   STATUS      current
   DESCRIPTION "SNMP V3 encryption type for the SNMP recipient."
   ::= { snmpNoticationRecipientTableEntry 10 }

-- END SNMP configuration

-- START CMA Server license configuration 
CmaConfigLicenseFeatureTableEntry    ::= SEQUENCE
{
   featureIndex          CmaDefaultTableIndexRange,
   featureLicense        FeatureLicense,
   enabled               TruthValue,
   licenseCount          Integer32,
   activatedDate         DateAndTime, 
   expirationDate        DateAndTime
}

cmaConfigLicenseFeatureTableEntry OBJECT-TYPE
   SYNTAX        CmaConfigLicenseFeatureTableEntry
   MAX-ACCESS    not-accessible
   STATUS        current
   DESCRIPTION   "CMA License feature table entry."
   INDEX         { featureIndex }
   ::= { cmaConfigLicenseFeatureTable 1 }

featureIndex OBJECT-TYPE
   SYNTAX      CmaDefaultTableIndexRange
   MAX-ACCESS  read-only
   STATUS      current
   DESCRIPTION "Feature index." 
   ::= { cmaConfigLicenseFeatureTableEntry 1 }

featureLicense         OBJECT-TYPE
   SYNTAX        FeatureLicense
   MAX-ACCESS    read-only
   STATUS        current
   DESCRIPTION   "Licensed feature."
   ::= { cmaConfigLicenseFeatureTableEntry 2}

FeatureLicense  ::= TEXTUAL-CONVENTION
   STATUS        current
   DESCRIPTION   "Licensed feature values."
   SYNTAX        INTEGER
                 {
                    dmaIntegration(2),
                    multiTenant(3),
                    managementOfEndpointsAndServices(11),
                    serviceProviderApi(22)
                 }

enabled OBJECT-TYPE
   SYNTAX      TruthValue
   MAX-ACCESS  read-only
   STATUS      current
   DESCRIPTION "Is feature enabled."
   DEFVAL      { false }
   ::= { cmaConfigLicenseFeatureTableEntry 3 }

licenseCount OBJECT-TYPE
   SYNTAX      Integer32
   MAX-ACCESS  read-only
   STATUS      current
   DESCRIPTION "License count.  If the license feature does not have an associated license count then the licenseCount 
                will  return -1 to indicate that the count is not applicable for this feature."
   DEFVAL      { 0 }
   ::= { cmaConfigLicenseFeatureTableEntry 4 }

activatedDate OBJECT-TYPE 
   SYNTAX      DateAndTime
   MAX-ACCESS  read-only
   STATUS      current
   DESCRIPTION "Activated date of license.  If there is no set date for the license activation then 1970-1-1,0:0:0.0 will be returned."
   ::= { cmaConfigLicenseFeatureTableEntry 5 }

expirationDate OBJECT-TYPE 
   SYNTAX      DateAndTime
   MAX-ACCESS  read-only
   STATUS      current
   DESCRIPTION "Expiration date of license.  If there is not set date for the license expiration then 9999-12-31,0:0:0.0 will be returned."
   ::= { cmaConfigLicenseFeatureTableEntry 6 }

cmaConfigLicenseGroup  OBJECT-GROUP
   OBJECTS
   {
      cmaConfigLicenseSystemSerialNumber,
      cmaConfigLicenseExpirationDays,
      cmaConfigLicenseCmadLicenseReclaimationThreshold,
      cmaConfigLicenseCmadLicenseReclaimationThresholdUnit,
      cmaConfigLicenseSupportedVersions,
      cmaConfigLicenseServerType,
      cmaConfigLicenseStatus,
      featureIndex,
      featureLicense,
      enabled,
      licenseCount,
      activatedDate,
      expirationDate
   }
STATUS current
   DESCRIPTION "CMA license configuration conformance group."
   ::= { cmaConfigConformance 23 }

cmaConfigLicenseSystemSerialNumber  OBJECT-TYPE
   SYNTAX       OCTET STRING (SIZE(0..255))
   MAX-ACCESS   read-only
   STATUS       current
   DESCRIPTION  "CMA license serial number."
   ::= { cmaConfigLicenses 1 }

cmaConfigLicenseExpirationDays  OBJECT-TYPE
   SYNTAX       Integer32 (0..90)
   MAX-ACCESS   read-only
   STATUS       current
   DESCRIPTION  "Returns how many days left before it expired only if 
                 the license will expire in 30 days, otherwise reutrn -1."
   ::= { cmaConfigLicenses 2 }

cmaConfigLicenseCmadLicenseReclaimationThreshold OBJECT-TYPE
   SYNTAX       Integer32 (0..90)
   MAX-ACCESS   read-only
   STATUS       current
   DESCRIPTION  "Value of License reclaim interval. E.g., if license reclaim interval is set to 5 minutes, and a CMAD has been offline for 5 minutes, it's license will be reclaimed. Set to 0 to not reclaim CMAD licenses."
   ::= { cmaConfigLicenses 3 }

cmaConfigLicenseSupportedVersions OBJECT-TYPE
   SYNTAX       OCTET STRING (SIZE(0..255))
   MAX-ACCESS   read-only
   STATUS       current
   DESCRIPTION  "Supported CMA versions."
   ::= { cmaConfigLicenses 4 }

cmaConfigLicenseServerType OBJECT-TYPE
   SYNTAX       CmaConfigLicenseServerType
   MAX-ACCESS   read-only
   STATUS       current
   DESCRIPTION  "The type of the CMA server."
   ::= { cmaConfigLicenses 5 }

CmaConfigLicenseServerType  ::= TEXTUAL-CONVENTION
   STATUS        current
   DESCRIPTION   "The type values of the CMA server."
   SYNTAX        INTEGER
                 {
                    primary(1),
                    secondary(2)
                 }

cmaConfigLicenseStatus OBJECT-TYPE
   SYNTAX       CmaConfigLicenseStatus
   MAX-ACCESS   read-only
   STATUS       current
   DESCRIPTION  "The status of the license."
   ::= { cmaConfigLicenses 6 }

CmaConfigLicenseStatus  ::= TEXTUAL-CONVENTION
   STATUS        current
   DESCRIPTION   "The status values of the license."
   SYNTAX        INTEGER
                 {
                    active(1),
                    inactive(2),
                    expired(3)
                 }

cmaConfigLicenseFeatureTable OBJECT-TYPE
   SYNTAX        SEQUENCE OF CmaConfigLicenseFeatureTableEntry
   MAX-ACCESS    not-accessible
   STATUS        current
   DESCRIPTION   "License feature table."
   ::= { cmaConfigLicenses 7 }

cmaConfigLicenseCmadLicenseReclaimationThresholdUnit OBJECT-TYPE
   SYNTAX       OCTET STRING (SIZE(0..255))
   MAX-ACCESS   read-only
   STATUS       current
   DESCRIPTION  "Unit of License reclaim interval. E.g., DAYS, HOURS, MINUTES. "
   ::= { cmaConfigLicenses 8 }

-- END CMA Server license configuration
-- START CMA Email Customization
cmaEmailCustomizationGroup  OBJECT-GROUP
   OBJECTS
   {
      cmaEmailCustomizationStart
,
      cmaEmailCustomizationEnd
   }
   STATUS current
   DESCRIPTION "CMA Email Customization conformance group."
   ::= { cmaConfigConformance 24 }

cmaEmailCustomizationStart OBJECT-TYPE
   SYNTAX       OCTET STRING (SIZE(0..650))
   MAX-ACCESS   read-only
   STATUS       current
   DESCRIPTION  "CMA Email Customization - Beginning of the scheduling reminder email "
   ::= { cmaEmailCustomization  1 }

cmaEmailCustomizationEnd OBJECT-TYPE
   SYNTAX       OCTET STRING (SIZE(0..650))
   MAX-ACCESS   read-only
   STATUS       current
   DESCRIPTION  "CMA Email Customization - End of the scheduling reminder email "
   ::= { cmaEmailCustomization  2 }
   
-- END CMA Email Customization

-- START CMA CDR Archive Settings
cmaConfigCDRArchiveSettingsGroup  OBJECT-GROUP
   OBJECTS
   {
      cmaConfigDaysToKeepEndpointCDRs,
      cmaConfigCDRArchiveEnabled,
      cmaConfigCDRArchiveFTPServer,
      cmaConfigCDRArchiveFTPPort,
      cmaConfigCDRArchiveUserName,
      cmaConfigCDRArchiveFTPDirectory
   }
   STATUS current
   DESCRIPTION "CMA CDR Archive Settings."
   ::= { cmaConfigConformance 25 }

cmaConfigDaysToKeepEndpointCDRs OBJECT-TYPE
   SYNTAX       Integer32 (0..60)
   MAX-ACCESS   read-only
   STATUS       current
   DESCRIPTION  "Number of days that Endpoint CDRs are retained on the CMA."
   ::= { cmaConfigCDRArchive 1 }

cmaConfigCDRArchiveEnabled OBJECT-TYPE
   SYNTAX       TruthValue
   MAX-ACCESS   read-only
   STATUS       current
   DESCRIPTION  "Flag indicating whether to archive Endpoint CDRs to an external FTP server in CSV Format." 
   ::= { cmaConfigCDRArchive 2 }

cmaConfigCDRArchiveFTPServer OBJECT-TYPE
   SYNTAX       OCTET STRING (SIZE(0..100))
   MAX-ACCESS   read-only
   STATUS       current
   DESCRIPTION  "Hostname or IP Address of FTP server to use for archive of Endpoint CDRs."
   ::= { cmaConfigCDRArchive 5 }

cmaConfigCDRArchiveFTPPort OBJECT-TYPE
   SYNTAX       Integer32 (1..65535)
   MAX-ACCESS   read-only
   STATUS       current
   DESCRIPTION  "FTP port of FTP server to use for archive of Endpoint CDRs."
   ::= { cmaConfigCDRArchive 6 }

cmaConfigCDRArchiveUserName OBJECT-TYPE
   SYNTAX       OCTET STRING (SIZE(0..100))
   MAX-ACCESS   read-only
   STATUS       current
   DESCRIPTION  "Username for the FTP server to use for archive of Endpoint CDRs."
   ::= { cmaConfigCDRArchive 7 }

cmaConfigCDRArchiveFTPDirectory OBJECT-TYPE
   SYNTAX       OCTET STRING (SIZE(0..100))
   MAX-ACCESS   read-only
   STATUS       current
   DESCRIPTION  "Directory on the FTP server to use for archive of Endpoint CDRs."
   ::= { cmaConfigCDRArchive 8 }

--cmaConfigLocalUserAccount Group

cmaConfigLocalUserAccountGroup   OBJECT-GROUP
   OBJECTS
   {
        cmaLocalUserFailedLoginThreshold,
        cmaLocalUSerFailedLoginWindow,
        cmaLocalUserAccountLockoutDuration,
        cmaLocalUserAccountThresholdAccount
   }
   STATUS current
   DESCRIPTION "CMA Local User Account config conformance group."
   ::= { cmaConfigConformance 26 }

cmaLocalUserFailedLoginThreshold   OBJECT-TYPE
   SYNTAX       Integer32
   MAX-ACCESS   read-only
   STATUS       current
   DESCRIPTION  "Number of failed logins allowed for a user. "
   ::= { cmaConfigLocalUserAccount  1 }

cmaLocalUSerFailedLoginWindow   OBJECT-TYPE
   SYNTAX       Integer32
   MAX-ACCESS   read-only
   STATUS       current
   DESCRIPTION  "Failed login window in hours for a particular user. "
   ::= { cmaConfigLocalUserAccount  2 }

cmaLocalUserAccountLockoutDuration   OBJECT-TYPE
   SYNTAX       Integer32
   MAX-ACCESS   read-only
   STATUS       current
   DESCRIPTION  "The account lockout duration (minutes) for user accounts which have exceeded the failed login threshold.  If the lockout is indefinite and must be manually unlocked, then this will have a value of -1."
   ::= { cmaConfigLocalUserAccount  3 }

cmaLocalUserAccountThresholdAccount   OBJECT-TYPE
   SYNTAX       Integer32
   MAX-ACCESS   read-only
   STATUS       current
   DESCRIPTION  "Customise Account Inactivity for the number of days "
   ::= { cmaConfigLocalUserAccount  4 }

--End ConfigLocalUserAccount Group

--Start Local Password Requirement Configuration

cmaConfigLocalPasswordRequirementGroup   OBJECT-GROUP
   OBJECTS
   {
      cmaLocalPasswordMinLen,
      cmaLocalPasswordMinChangedChar,
      cmaLocalPasswordMinAgeCheck,
      cmaLocalPasswordMinAge,
      cmaLocalPasswordMaxAgeCheck,      
      cmaLocalPasswordMaxAge,
      cmaLocalPasswordWarningIntervalCheck,
      cmaLocalPasswordWarningInterval,
      cmaLocalPasswordRejectPreviousCheck,      
      cmaLocalPasswordRejectPrevious,
      cmaLocalPasswordIncludeLowerCase, 
      cmaLocalPasswordLowerCaseCount,
      cmaLocalPasswordIncludeUpperCase,
      cmaLocalPasswordUpperCaseCount,
      cmaLocalPasswordIncludeNumbers,
      cmaLocalPasswordNumbersCount,
      cmaLocalPasswordIncludeSpecialChars,
      cmaLocalPasswordSpecialCharsCount,
      cmaLocalPasswordConsecutive,
      cmaLocalPasswordConsecutiveCount

   }  
   STATUS current
   DESCRIPTION "CMA Local Password Requirement config conformance group."
   ::= { cmaConfigConformance 27 }

cmaLocalPasswordMinLen   OBJECT-TYPE
   SYNTAX       Integer32
   MAX-ACCESS   read-only
   STATUS       current
   DESCRIPTION  "Minimum Length of the Password."
   ::= { cmaConfigLocalPasswordRequirement  1 }

cmaLocalPasswordMinChangedChar   OBJECT-TYPE
   SYNTAX       Integer32
   MAX-ACCESS   read-only
   STATUS       current
   DESCRIPTION  "Minimum number of changed characters in the password."
   ::= { cmaConfigLocalPasswordRequirement  2 }

cmaLocalPasswordMinAgeCheck   OBJECT-TYPE
   SYNTAX       TruthValue
   MAX-ACCESS   read-only
   STATUS       current
   DESCRIPTION  "Check for the minimum age of LocalPassword."
   ::= { cmaConfigLocalPasswordRequirement  3 }

cmaLocalPasswordMinAge   OBJECT-TYPE
   SYNTAX       Integer32
   MAX-ACCESS   read-only
   STATUS       current
   DESCRIPTION  "Minimum Age of password allowed."
   ::= { cmaConfigLocalPasswordRequirement  4 }

cmaLocalPasswordMaxAgeCheck   OBJECT-TYPE
   SYNTAX       TruthValue
   MAX-ACCESS   read-only
   STATUS       current
   DESCRIPTION  "Check for the max age the password allowed."
   ::= { cmaConfigLocalPasswordRequirement  5 }

cmaLocalPasswordMaxAge   OBJECT-TYPE
   SYNTAX       Integer32
   MAX-ACCESS   read-only
   STATUS       current
   DESCRIPTION  "Max age of the password allowed."
   ::= { cmaConfigLocalPasswordRequirement  6 }

cmaLocalPasswordWarningIntervalCheck   OBJECT-TYPE
   SYNTAX       TruthValue
   MAX-ACCESS   read-only
   STATUS       current
   DESCRIPTION  "check for password warning  inteval in days."
   ::= { cmaConfigLocalPasswordRequirement  7 }

cmaLocalPasswordWarningInterval   OBJECT-TYPE
   SYNTAX       Integer32
   MAX-ACCESS   read-only
   STATUS       current
   DESCRIPTION  "Password warning interval."
   ::= { cmaConfigLocalPasswordRequirement  8 }


cmaLocalPasswordRejectPreviousCheck   OBJECT-TYPE
   SYNTAX       TruthValue
   MAX-ACCESS   read-only
   STATUS       current
   DESCRIPTION  "Reject previous passwords checkbox ."
   ::= { cmaConfigLocalPasswordRequirement  9 }

cmaLocalPasswordRejectPrevious   OBJECT-TYPE
   SYNTAX       Integer32
   MAX-ACCESS   read-only
   STATUS       current
   DESCRIPTION  "Reject previous passwords checkbox ."
   ::= { cmaConfigLocalPasswordRequirement  10 }

cmaLocalPasswordIncludeLowerCase   OBJECT-TYPE
   SYNTAX       TruthValue
   MAX-ACCESS   read-only
   STATUS       current
   DESCRIPTION  "Allow lower cases to be included in the  passsword ."
   ::= { cmaConfigLocalPasswordRequirement  11 }

cmaLocalPasswordLowerCaseCount   OBJECT-TYPE
   SYNTAX       Integer32
   MAX-ACCESS   read-only
   STATUS       current
   DESCRIPTION  "number of  lower case characters included ."
   ::= { cmaConfigLocalPasswordRequirement  12 }

cmaLocalPasswordIncludeUpperCase   OBJECT-TYPE
   SYNTAX       TruthValue
   MAX-ACCESS   read-only
   STATUS       current
   DESCRIPTION  "Include upper case in the password ."
   ::= { cmaConfigLocalPasswordRequirement  13 }

cmaLocalPasswordUpperCaseCount   OBJECT-TYPE
   SYNTAX       Integer32
   MAX-ACCESS   read-only
   STATUS       current
   DESCRIPTION  " number of upper case characters included."
   ::= { cmaConfigLocalPasswordRequirement  14 }

cmaLocalPasswordIncludeNumbers   OBJECT-TYPE
   SYNTAX       TruthValue
   MAX-ACCESS   read-only
   STATUS       current
   DESCRIPTION  "Include numbers in the password ."
   ::= { cmaConfigLocalPasswordRequirement  15 }

cmaLocalPasswordNumbersCount   OBJECT-TYPE
   SYNTAX       Integer32
   MAX-ACCESS   read-only
   STATUS       current
   DESCRIPTION  "number of numbers allowed in the password ."
   ::= { cmaConfigLocalPasswordRequirement  16 }

cmaLocalPasswordIncludeSpecialChars   OBJECT-TYPE
   SYNTAX       TruthValue
   MAX-ACCESS   read-only
   STATUS       current
   DESCRIPTION  "Include special characters in the password ."
   ::= { cmaConfigLocalPasswordRequirement  17 }

cmaLocalPasswordSpecialCharsCount   OBJECT-TYPE
   SYNTAX       Integer32
   MAX-ACCESS   read-only
   STATUS       current
   DESCRIPTION  "number of special characters in the password."
   ::= { cmaConfigLocalPasswordRequirement  18 }

cmaLocalPasswordConsecutive   OBJECT-TYPE
   SYNTAX       TruthValue
   MAX-ACCESS   read-only
   STATUS       current
   DESCRIPTION  "Include consecutive repetition of characters."
   ::= { cmaConfigLocalPasswordRequirement  19 }

cmaLocalPasswordConsecutiveCount   OBJECT-TYPE
   SYNTAX       Integer32
   MAX-ACCESS   read-only
   STATUS       current
   DESCRIPTION  "number of repetition of the same character in the password."
   ::= { cmaConfigLocalPasswordRequirement  20 }


--End Local Password Requirement Configuration


-------------------------------------------------------------------------------
-- Status Group
-------------------------------------------------------------------------------

-- START Connected User status 
cmaStatusUsersGroup  OBJECT-GROUP
   OBJECTS
   {
      connectedUserCount,
      connectedAdminUserCount,
      connectedOperatorUserCount,
      connectedSchedulerUserCount,
      connectedAuditorUserCount,
      connectedUserIndex,
      connectedUserName,
      connectedUserRole,
      connectedUserLoginTime
   }
   STATUS current
   DESCRIPTION "CMA connected user status conformance group."
   ::= { cmaStatusConformance 1 }

connectedUserCount   OBJECT-TYPE
   SYNTAX Integer32
   MAX-ACCESS read-only
   STATUS current
   DESCRIPTION "Total number of connected CMA users."
   ::= { cmaStatusUsers 1 }

connectedAdminUserCount   OBJECT-TYPE
   SYNTAX Integer32
   MAX-ACCESS read-only
   STATUS current
   DESCRIPTION "Number of connected Administrator users."
   ::= { cmaStatusUsers 2 }

connectedOperatorUserCount   OBJECT-TYPE
   SYNTAX Integer32
   MAX-ACCESS read-only
   STATUS current
   DESCRIPTION "Number of connected Operator users."
   ::= { cmaStatusUsers 3 }

connectedSchedulerUserCount   OBJECT-TYPE
   SYNTAX Integer32
   MAX-ACCESS read-only
   STATUS current
   DESCRIPTION "Number of connected Scheduler users."
   ::= { cmaStatusUsers 4 }

connectedAuditorUserCount   OBJECT-TYPE
   SYNTAX Integer32
   MAX-ACCESS read-only
   STATUS current
   DESCRIPTION "Number of connected Scheduler users."
   ::= { cmaStatusUsers 5 }

-- Connected User table 
ConnectedUserTableRange ::= Integer32 (1..255)
ConnectedUserTableEntry ::= SEQUENCE
{
   connectedUserIndex      ConnectedUserTableRange,
   connectedUserName       OCTET STRING,
   connectedUserRole       OCTET STRING,
   connectedUserLoginTime  DateAndTime
}

connectedUserTable OBJECT-TYPE
   SYNTAX        SEQUENCE OF ConnectedUserTableEntry
   MAX-ACCESS    not-accessible
   STATUS        current
   DESCRIPTION   "Connected user table. Contains the names, roles, and login times 
                  of the connected users."
   ::= { cmaStatusUsers 6 }

connectedUserTableEntry OBJECT-TYPE
   SYNTAX        ConnectedUserTableEntry
   MAX-ACCESS    not-accessible
   STATUS        current
   DESCRIPTION   "Connected user table entry."
   INDEX         { connectedUserIndex }
   ::= { connectedUserTable 1 }

connectedUserIndex OBJECT-TYPE
   SYNTAX      ConnectedUserTableRange
   MAX-ACCESS  read-only
   STATUS      current
   DESCRIPTION "Unique system-assigned ID for this entry." 
   ::= { connectedUserTableEntry 1 }

connectedUserName OBJECT-TYPE 
   SYNTAX      OCTET STRING (SIZE(0..255))
   MAX-ACCESS  read-only
   STATUS      current
   DESCRIPTION "Name of the connected user."
   ::= { connectedUserTableEntry 2 }

connectedUserRole OBJECT-TYPE 
   SYNTAX      OCTET STRING (SIZE(0..255))
   MAX-ACCESS  read-only
   STATUS      current
   DESCRIPTION "Role of the connected user."
   ::= { connectedUserTableEntry 3 }
   
connectedUserLoginTime OBJECT-TYPE 
   SYNTAX      DateAndTime
   MAX-ACCESS  read-only
   STATUS      current
   DESCRIPTION "Login time of the connected user."
   ::= { connectedUserTableEntry 4 }

-- END Connected User status

-- START CMA Server license status
cmaStatusLicenseGroup  OBJECT-GROUP
   OBJECTS
   {
      cmaLicenseSeatCount,
      cmaLicenseSeatsInUse
   }
   STATUS current
   DESCRIPTION "CMA license status conformance group."
   ::= { cmaStatusConformance 3 }

cmaLicenseSeatCount OBJECT-TYPE
   SYNTAX       Integer32
   MAX-ACCESS   read-only
   STATUS       current
   DESCRIPTION  "Total number of CMAD seats in the license."
   ::= { cmaStatusLicenses 1 }

cmaLicenseSeatsInUse OBJECT-TYPE
   SYNTAX       Integer32
   MAX-ACCESS   read-only
   STATUS       current
   DESCRIPTION  "Number of licensed seats in use."
   ::= { cmaStatusLicenses 2 }

-- END CMA Server license status


-- START scheduled endpoint management status
cmaStatusEndpointManagementGroup  OBJECT-GROUP
   OBJECTS
   {
--      cmaEpManagementPendingSoftUpdates,
      cmaEpManagementInProgressSoftUpdates,
--      cmaEpManagementSucessfulSoftUpdates,
--      cmaEpManagementFailedSoftUpdates,
--      cmaEpManagementPendingProvisioning,
      cmaEpManagementInProgressProvisioning
--      cmaEpManagementSucessfulProvisioning,
--      cmaEpManagementFailedProvisioning
   }
   STATUS current
   DESCRIPTION "CMA endpoint management status conformance group."
   ::= { cmaStatusConformance 6 }

cmaEpManagementInProgressSoftUpdates OBJECT-TYPE
   SYNTAX       Integer32
   MAX-ACCESS   read-only
   STATUS       current
   DESCRIPTION  "Number of in-progress endpoint soft updates."
   ::= { cmaStatusEndpointManagement 1 }

cmaEpManagementInProgressProvisioning OBJECT-TYPE
   SYNTAX       Integer32
   MAX-ACCESS   read-only
   STATUS       current
   DESCRIPTION  "Number of in-progress endpoint provisioning jobs."
   ::= { cmaStatusEndpointManagement 2 }

--cmaEpManagementPendingSoftUpdates OBJECT-TYPE
--   SYNTAX       Integer32
--   MAX-ACCESS   read-only
--   STATUS       current
--   DESCRIPTION  "Number of pending endpoint soft updates."
--   ::= { cmaStatusEndpointManagement 1 }

--cmaEpManagementSucessfulSoftUpdates OBJECT-TYPE
--   SYNTAX       Integer32
--   MAX-ACCESS   read-only
--   STATUS       current
--   DESCRIPTION  "Number of sucessful soft updates."
--   ::= { cmaStatusEndpointManagement 4 }

--cmaEpManagementFailedSoftUpdates OBJECT-TYPE
--   SYNTAX       Integer32
--   MAX-ACCESS   read-only
--   STATUS       current
--   DESCRIPTION  "Number of failed soft updates."
--   ::= { cmaStatusEndpointManagement 5 }

--cmaEpManagementPendingProvisioning OBJECT-TYPE
--   SYNTAX       Integer32
--   MAX-ACCESS   read-only
--   STATUS       current
--   DESCRIPTION  "Number of pending endpoint provisioning jobs."
--   ::= { cmaStatusEndpointManagement 6 }

--cmaEpManagementSucessfulProvisioning OBJECT-TYPE
--   SYNTAX       Integer32
--   MAX-ACCESS   read-only
--   STATUS       current
--   DESCRIPTION  "Number of sucessful provisioning jobs."
--   ::= { cmaStatusEndpointManagement 8 }

--cmaEpManagementFailedProvisioning OBJECT-TYPE
--   SYNTAX       Integer32
--   MAX-ACCESS   read-only
--   STATUS       current
--   DESCRIPTION  "Number of failed provisioning jobs."
--   ::= { cmaStatusEndpointManagement 9 }

-- END scheduled endpoint management status

-- START MCU status
cmaStatusDeviceGroup  OBJECT-GROUP
   OBJECTS
   {
      cmaMcuCount,
      cmaMcuCountWithWarnings,
      cmaMcuCountWithErrors,
      cmaMcuIndex,
      cmaMcuName,
      cmaMcuType,
      cmaMcuInetAddressType,
      cmaMcuInetAddress,
      cmaMcuStatus,
      cmaMcuConferenceCount,
      cmaMcuAudioPortsUsed,
      cmaMcuVideoPortsUsed,
      cmaEndpointCount,
      cmaEndpointCountWithAlerts,
      cmaEndpointCountWithHelpRequests,
      cmaEndpointCountOnline,
      cmaEndpointCountOffline,
      cmaEndpointCountInCall,
      cmaEndpointIndex,
      cmaEndpointId,            
      cmaEndpointOwner,
      cmaEndpointIsdnVideoNumber,
      cmaEndpointSoftwareVersion,    
      cmaEndpointType,
      cmaEndpointInetAddressType,
      cmaEndpointInetAddress,
      cmaEndpointStatus,
      cmaEndpointInCall,
      cmaEndpointGatekeeperRegStatus,
      cmaEndpointGabRegStatus,
      cmaEndpointPresenceRegStatus,
      cmaEndpointSipRegStatus,
      cmaEndpointManagementStatus,
      cmaEndpointErrorCount,
      cmaEndpointErrors,
      cmaEndpointWarningCount,
      cmaEndpointWarnings,
      cmaEndpointHelpRequest,
      cmaEndpointSerialNumber,  
      cmaEndpointAvailableToSchedule,
      cmaEndpointRegisteredAliases,         
      cmaEndpointSipUri,
      cmaEndpointGatekeeperAddress,
      cmaEndpointSipServerAddress,          
      cmaVbpCount,
      cmaVbpIndex,
      cmaVbpModel,
      cmaVbpName,
      cmaVbpLanInetAddressType,
      cmaVbpLanInetAddress,
      cmaVbpWanInetAddressType,
      cmaVbpWanInetAddress,
      cmaDmaCount,
      cmaDmaIndex,
      cmaDmaName,
      cmaDmaInetAddressType,
      cmaDmaInetAddress,
      cmaDmaStatus,
      cmaDmaIsCallServer,
      cmaDmaIsConferenceManager,
      cmaDmaH323Enabled,
      cmaDmaSipEnabled,
      cmaDmaSiteTopologyIntegrated,    
      cmaEndpointExchangeStatus,
      cmaEndpointPeripheralIconState,
      cmaEndpointPeripheralStatus,
      cmaPeripheralIndex,
      cmaPeripheralPairedStatus,
      cmaPeripheralAlertState,
      cmaPeripheralPairedName,
      cmaPeripheralDeviceType,
      cmaPeripheralSerialNumber,
      cmaPeripheralInetAddress,
      cmaPeripheralInetAddressType,
      cmaPeripheralHardwareVersion,
      cmaPeripheralSoftwareVersion,
      cmaPeripheralCount,
      cmaRpadCount,
      cmaRpadIndex,
      cmaRpadName,
      cmaRpadStatus,
      cmaRpadProviderSideAddress,
      cmaRpadSiteName,
      cmaSbcCount,
      cmaSbcIndex,
      cmaSbcName,
      cmaSbcLanInetAddressType,
      cmaSbcLanInetAddress,
      cmaSbcWanInetAddressType,
      cmaSbcWanInetAddress  
   }
   STATUS current
   DESCRIPTION "CMA device status conformance group."
   ::= { cmaStatusConformance 7 }

cmaMcuCount OBJECT-TYPE
   SYNTAX       Integer32
   MAX-ACCESS   read-only
   STATUS       current
   DESCRIPTION  "Total number of MCUs known to the CMA server."
   ::= { cmaStatusDeviceMCU 1 }

cmaMcuCountWithWarnings OBJECT-TYPE
   SYNTAX       Integer32
   MAX-ACCESS   read-only
   STATUS       current
   DESCRIPTION  "Number of MCUs with warnings."
   ::= { cmaStatusDeviceMCU 2 }

cmaMcuCountWithErrors OBJECT-TYPE
   SYNTAX       Integer32
   MAX-ACCESS   read-only
   STATUS       current
   DESCRIPTION  "Number of MCUs with errors."
   ::= { cmaStatusDeviceMCU 3 }

CmaMcuStatusTableEntry    ::= SEQUENCE
{
   cmaMcuIndex                  CmaDefaultTableIndexRange,
   cmaMcuName                   OCTET STRING,
   cmaMcuType                   CmaMcuType,
   cmaMcuInetAddressType        InetAddressType, 
   cmaMcuInetAddress            InetAddress,
   cmaMcuStatus                 CmaDeviceStatus,
   cmaMcuConferenceCount        Integer32,          -- Number of active conferences
   cmaMcuAudioPortsUsed         Integer32,          -- % of audio ports in use
   cmaMcuVideoPortsUsed         Integer32           -- % of video ports in use
}

cmaMcuStatusTable     OBJECT-TYPE
   SYNTAX       SEQUENCE OF CmaMcuStatusTableEntry
   MAX-ACCESS   not-accessible
   STATUS       current
   DESCRIPTION  "MCU status table. Contains identification, status, 
                 and usage information for MCUs."
   ::= { cmaStatusDeviceMCU 4 }

cmaMcuStatusTableEntry    OBJECT-TYPE
   SYNTAX       CmaMcuStatusTableEntry
   MAX-ACCESS   not-accessible
   STATUS       current
   DESCRIPTION  "MCU status table entry."
   INDEX        { cmaMcuIndex }
   ::= { cmaMcuStatusTable 1 }

cmaMcuIndex     OBJECT-TYPE
   SYNTAX       CmaDefaultTableIndexRange 
   MAX-ACCESS   read-only 
   STATUS       current
   DESCRIPTION  "Unique system-assigned ID for this entry." 
   ::= { cmaMcuStatusTableEntry 1 }

cmaMcuName     OBJECT-TYPE
   SYNTAX       OCTET STRING (SIZE(1..255)) 
   MAX-ACCESS   read-only 
   STATUS       current
   DESCRIPTION  "Name of the MCU."
   ::= { cmaMcuStatusTableEntry 2 }

cmaMcuType      OBJECT-TYPE
   SYNTAX       CmaMcuType 
   MAX-ACCESS   read-only 
   STATUS       current
   DESCRIPTION  "MCU type."
   ::= { cmaMcuStatusTableEntry 3 }

cmaMcuInetAddressType      OBJECT-TYPE
   SYNTAX       InetAddressType 
   MAX-ACCESS   read-only 
   STATUS       current
   DESCRIPTION  " IP address type of the MCU."
   ::= { cmaMcuStatusTableEntry 4 }

cmaMcuInetAddress      OBJECT-TYPE
   SYNTAX       InetAddress
   MAX-ACCESS   read-only 
   STATUS       current
   DESCRIPTION  "IP address of the MCU."
   ::= { cmaMcuStatusTableEntry 5 }

cmaMcuStatus          OBJECT-TYPE
   SYNTAX       CmaDeviceStatus
   MAX-ACCESS   read-only 
   STATUS       current
   DESCRIPTION  "Status of the MCU."
   ::= { cmaMcuStatusTableEntry 6 }

cmaMcuConferenceCount          OBJECT-TYPE
   SYNTAX       Integer32
   MAX-ACCESS   read-only 
   STATUS       current
   DESCRIPTION  "Number of active conferences on the MCU."
   ::= { cmaMcuStatusTableEntry 7 }

cmaMcuAudioPortsUsed          OBJECT-TYPE
   SYNTAX       Integer32
   MAX-ACCESS   read-only 
   STATUS       current
   DESCRIPTION  "Percentage of audio ports in use on the MCU."
   ::= { cmaMcuStatusTableEntry 8 }

cmaMcuVideoPortsUsed          OBJECT-TYPE
   SYNTAX       Integer32
   MAX-ACCESS   read-only 
   STATUS       current
   DESCRIPTION  "Percentage of video ports in use on the MCU."
   ::= { cmaMcuStatusTableEntry 9 }

-- END MCU status

-- START endpoint status

cmaEndpointCount OBJECT-TYPE
   SYNTAX       Integer32
   MAX-ACCESS   read-only
   STATUS       current
   DESCRIPTION  "Total number of endpoints known to the CMA server."
   ::= { cmaStatusDeviceEndpoint 1 }

cmaEndpointCountWithAlerts OBJECT-TYPE
   SYNTAX       Integer32
   MAX-ACCESS   read-only
   STATUS       current
   DESCRIPTION  "Number of endpoints with alert conditions."
   ::= { cmaStatusDeviceEndpoint 2 }

cmaEndpointCountWithHelpRequests OBJECT-TYPE
   SYNTAX       Integer32
   MAX-ACCESS   read-only
   STATUS       current
   DESCRIPTION  "Number of endpoints with help requests."
   ::= { cmaStatusDeviceEndpoint 3 }

cmaEndpointCountOnline OBJECT-TYPE
   SYNTAX       Integer32
   MAX-ACCESS   read-only
   STATUS       current
   DESCRIPTION  "Number of endpoints that are on line."
   ::= { cmaStatusDeviceEndpoint 4 }

cmaEndpointCountOffline OBJECT-TYPE
   SYNTAX       Integer32
   MAX-ACCESS   read-only
   STATUS       current
   DESCRIPTION  "Number of endpoints that are off line."
   ::= { cmaStatusDeviceEndpoint 5 }

cmaEndpointCountInCall OBJECT-TYPE
   SYNTAX       Integer32
   MAX-ACCESS   read-only
   STATUS       current
   DESCRIPTION  "Number of endpoints that are in a call."
   ::= { cmaStatusDeviceEndpoint 6 }

CmaEndpointStatusTableEntry          ::= SEQUENCE
{
   cmaEndpointIndex                  CmaDefaultTableIndexRange,
   cmaEndpointType                   CmaEndpointType,
   cmaEndpointId                     Integer32,
   cmaEndpointOwner                  OCTET STRING,
   cmaEndpointIsdnVideoNumber        OCTET STRING,
   cmaEndpointInetAddressType        InetAddressType,
   cmaEndpointInetAddress            InetAddress,
   cmaEndpointStatus                 CmaDeviceStatus,   -- online or offline
   cmaEndpointInCall                 TruthValue,
   cmaEndpointGatekeeperRegStatus    CmaDeviceRegistrationStatus,
   cmaEndpointGabRegStatus           CmaDeviceRegistrationStatus,
   cmaEndpointPresenceRegStatus      CmaDeviceRegistrationStatus,
   cmaEndpointSipRegStatus           CmaDeviceRegistrationStatus,
   cmaEndpointManagementStatus       CmaDeviceManagementStatus,
   cmaEndpointErrorCount             Integer32,
   cmaEndpointErrors                 OCTET STRING,
   cmaEndpointWarningCount           Integer32,
   cmaEndpointWarnings               OCTET STRING,
   cmaEndpointHelpRequest            TruthValue,
   cmaEndpointExchangeStatus         CmaDeviceRegistrationStatus,
   cmaEndpointPeripheralIconState    CmaPeripheralIconState,
   cmaEndpointPeripheralStatus       CmaPeripheralPairingStatus,
   cmaEndpointSoftwareVersion        OCTET STRING,                       
   cmaEndpointSerialNumber           OCTET STRING,      
   cmaEndpointAvailableToSchedule    TruthValue,
   cmaEndpointRegisteredAliases      OCTET STRING,      
   cmaEndpointSipUri                 OCTET STRING,
   cmaEndpointGatekeeperAddress      InetAddress,
   cmaEndpointSipServerAddress       InetAddress
}

cmaEndpointStatusTable      OBJECT-TYPE
   SYNTAX        SEQUENCE OF CmaEndpointStatusTableEntry
   MAX-ACCESS    not-accessible
   STATUS        current
   DESCRIPTION   "Endpoint status table. Contains identification 
                  and status information for endpoints."
   ::= { cmaStatusDeviceEndpoint 7 }

cmaEndpointStatusTableEntry      OBJECT-TYPE
   SYNTAX        CmaEndpointStatusTableEntry
   MAX-ACCESS    not-accessible
   STATUS        current
   DESCRIPTION   "Endpoint status table entry."
   INDEX         { cmaEndpointIndex }
   ::= { cmaEndpointStatusTable 1}

cmaEndpointIndex         OBJECT-TYPE
   SYNTAX        CmaDefaultTableIndexRange
   MAX-ACCESS    read-only
   STATUS        current
   DESCRIPTION   "Unique system-assigned ID for this entry." 
   ::= { cmaEndpointStatusTableEntry 1 }

cmaEndpointType         OBJECT-TYPE
   SYNTAX        CmaEndpointType
   MAX-ACCESS    read-only
   STATUS        current
   DESCRIPTION   "Type of endpoint."
   ::= { cmaEndpointStatusTableEntry 2 }

cmaEndpointId         OBJECT-TYPE
   SYNTAX        Integer32
   MAX-ACCESS    read-only
   STATUS        current
   DESCRIPTION   "Id of endpoint."
   ::= { cmaEndpointStatusTableEntry 3 }


cmaEndpointOwner         OBJECT-TYPE
   SYNTAX        OCTET STRING
   MAX-ACCESS    read-only
   STATUS        current
   DESCRIPTION   "Endpoint Owner."
   ::= { cmaEndpointStatusTableEntry 4 }

cmaEndpointIsdnVideoNumber         OBJECT-TYPE
   SYNTAX        OCTET STRING
   MAX-ACCESS    read-only
   STATUS        current
   DESCRIPTION   "Endpoint Isdn Video Number."
   ::= { cmaEndpointStatusTableEntry 5 }

cmaEndpointInetAddressType         OBJECT-TYPE
   SYNTAX        InetAddressType
   MAX-ACCESS    read-only
   STATUS        current
   DESCRIPTION   "IP address type of the endpoint."
   ::= { cmaEndpointStatusTableEntry 6}

cmaEndpointInetAddress         OBJECT-TYPE
   SYNTAX        InetAddress
   MAX-ACCESS    read-only
   STATUS        current
   DESCRIPTION   "IP address of the endpoint."
   ::= { cmaEndpointStatusTableEntry 7 }

cmaEndpointStatus         OBJECT-TYPE
   SYNTAX        CmaDeviceStatus
   MAX-ACCESS    read-only
   STATUS        current
   DESCRIPTION   "Status of the endpoint."
   ::= { cmaEndpointStatusTableEntry 8 }

cmaEndpointInCall         OBJECT-TYPE
   SYNTAX        TruthValue
   MAX-ACCESS    read-only
   STATUS        current
   DESCRIPTION   "Flag indicating whether the endpoint is in a call."
   ::= { cmaEndpointStatusTableEntry 9 }

cmaEndpointGatekeeperRegStatus         OBJECT-TYPE
   SYNTAX        CmaDeviceRegistrationStatus
   MAX-ACCESS    read-only
   STATUS        current
   DESCRIPTION   "Gatekeeper registration status of the endpoint."
   ::= { cmaEndpointStatusTableEntry 10 }

cmaEndpointGabRegStatus         OBJECT-TYPE
   SYNTAX        CmaDeviceRegistrationStatus
   MAX-ACCESS    read-only
   STATUS        current
   DESCRIPTION   "GAB registration status of the endpoint."
   ::= { cmaEndpointStatusTableEntry 11 }

cmaEndpointPresenceRegStatus         OBJECT-TYPE
   SYNTAX        CmaDeviceRegistrationStatus
   MAX-ACCESS    read-only
   STATUS        current
   DESCRIPTION   "Presence registration status of the endpoint."
   ::= { cmaEndpointStatusTableEntry 12 }

cmaEndpointSipRegStatus         OBJECT-TYPE
   SYNTAX        CmaDeviceRegistrationStatus
   MAX-ACCESS    read-only
   STATUS        current
   DESCRIPTION   "SIP registration status of the endpoint."
   ::= { cmaEndpointStatusTableEntry 13 }

cmaEndpointManagementStatus         OBJECT-TYPE
   SYNTAX        CmaDeviceManagementStatus
   MAX-ACCESS    read-only
   STATUS        current
   DESCRIPTION   "Management status of the endpoint."
   ::= { cmaEndpointStatusTableEntry 14 }

cmaEndpointErrorCount         OBJECT-TYPE
   SYNTAX        Integer32
   MAX-ACCESS    read-only
   STATUS        current
   DESCRIPTION   "Number of errors on the endpoint."
   ::= { cmaEndpointStatusTableEntry 15 }

cmaEndpointErrors         OBJECT-TYPE
   SYNTAX        OCTET STRING
   MAX-ACCESS    read-only
   STATUS        current
   DESCRIPTION   "List of the errors on the endpoint, separated by 
                  new-line characters." 
   ::= { cmaEndpointStatusTableEntry 16 }

cmaEndpointWarningCount         OBJECT-TYPE
   SYNTAX        Integer32
   MAX-ACCESS    read-only
   STATUS        current
   DESCRIPTION   "Number of warnings on the endpoint."
   ::= { cmaEndpointStatusTableEntry 17 }

cmaEndpointWarnings         OBJECT-TYPE
   SYNTAX        OCTET STRING
   MAX-ACCESS    read-only
   STATUS        current
   DESCRIPTION   "List of the warnings on the endpoint, separated by 
                  new-line characters." 
   ::= { cmaEndpointStatusTableEntry 18 }

cmaEndpointHelpRequest         OBJECT-TYPE
   SYNTAX        TruthValue
   MAX-ACCESS    read-only
   STATUS        current
   DESCRIPTION   "Flag indicating whether there is a help request on the endpoint."
   ::= { cmaEndpointStatusTableEntry 19 }

cmaEndpointExchangeStatus         OBJECT-TYPE
   SYNTAX        CmaDeviceRegistrationStatus
   MAX-ACCESS    read-only
   STATUS        current
   DESCRIPTION   "Exchange server status of user associated with the endpoint."
   ::= { cmaEndpointStatusTableEntry 20 }

cmaEndpointPeripheralIconState         OBJECT-TYPE
    SYNTAX        CmaPeripheralIconState
    MAX-ACCESS    read-only
    STATUS        current
    DESCRIPTION   "Peripheral icon state for this endpoint."
    ::= { cmaEndpointStatusTableEntry 21 }

cmaEndpointPeripheralStatus         OBJECT-TYPE
    SYNTAX        CmaPeripheralPairingStatus
    MAX-ACCESS    read-only
    STATUS        current
    DESCRIPTION   "Peripheral status for this endpoint."
    ::= { cmaEndpointStatusTableEntry 22 }

cmaEndpointSoftwareVersion         OBJECT-TYPE
    SYNTAX        OCTET STRING
    MAX-ACCESS    read-only
    STATUS        current
    DESCRIPTION   "Software Version running on this endpoint."
    ::= { cmaEndpointStatusTableEntry 23 }
   
cmaEndpointSerialNumber         OBJECT-TYPE
    SYNTAX        OCTET STRING
    MAX-ACCESS    read-only
    STATUS        current
    DESCRIPTION   "Serial Number of this endpoint."
    ::= { cmaEndpointStatusTableEntry 24 }

cmaEndpointAvailableToSchedule         OBJECT-TYPE
    SYNTAX        TruthValue
    MAX-ACCESS    read-only
    STATUS        current
    DESCRIPTION   " Returns True if the Endpoint id available."
    ::= { cmaEndpointStatusTableEntry 25}

cmaEndpointRegisteredAliases         OBJECT-TYPE
    SYNTAX        OCTET STRING
    MAX-ACCESS    read-only
    STATUS        current
    DESCRIPTION   "Comma seperated list of gatekeeper registered aliases for this endpoint."
    ::= { cmaEndpointStatusTableEntry 26} 

cmaEndpointSipUri         OBJECT-TYPE
    SYNTAX        OCTET STRING
    MAX-ACCESS    read-only
    STATUS        current
    DESCRIPTION   "SipUri associated with this endpoint."
    ::= { cmaEndpointStatusTableEntry 27}

cmaEndpointGatekeeperAddress         OBJECT-TYPE
    SYNTAX        InetAddress
    MAX-ACCESS    read-only
    STATUS        current
    DESCRIPTION   "Host or IP address of the H.323 Gatekeeper for the endpoint."
    ::= { cmaEndpointStatusTableEntry 28}

cmaEndpointSipServerAddress        OBJECT-TYPE
    SYNTAX        InetAddress
    MAX-ACCESS    read-only
    STATUS        current
    DESCRIPTION   "Host or IP address of the SIP Server for the endpoint."
    ::= { cmaEndpointStatusTableEntry 29}

-- END endpoint status

-- START VBP status
cmaVbpCount OBJECT-TYPE
   SYNTAX       Integer32
   MAX-ACCESS   read-only
   STATUS       current
   DESCRIPTION  "Number of VBPs known to the CMA server."
   ::= { cmaStatusDeviceVBP 1 }

CmaVbpStatusTableEntry ::= SEQUENCE
{
   cmaVbpIndex                           CmaDefaultTableIndexRange,
   cmaVbpModel                           CmaVbpModel,
   cmaVbpName                            OCTET STRING,
   cmaVbpLanInetAddressType     InetAddressType,
   cmaVbpLanInetAddress         InetAddress,
   cmaVbpWanInetAddressType   InetAddressType,
   cmaVbpWanInetAddress       InetAddress
}

cmaVbpStatusTable      OBJECT-TYPE
   SYNTAX        SEQUENCE OF CmaVbpStatusTableEntry
   MAX-ACCESS    not-accessible
   STATUS        current
   DESCRIPTION   "VBP status table. Contains information about 
                  Polycom Video Border Proxy devices."
   ::= { cmaStatusDeviceVBP 2 }

cmaVbpStatusTableEntry      OBJECT-TYPE
   SYNTAX        CmaVbpStatusTableEntry
   MAX-ACCESS    not-accessible
   STATUS        current
   DESCRIPTION   "VBP status table entry."
   INDEX         { cmaVbpIndex }
   ::= { cmaVbpStatusTable 1}

cmaVbpIndex         OBJECT-TYPE
   SYNTAX        CmaDefaultTableIndexRange
   MAX-ACCESS    read-only
   STATUS        current
   DESCRIPTION   "Unique system-assigned ID for this entry." 
   ::= { cmaVbpStatusTableEntry 1 }

cmaVbpModel         OBJECT-TYPE
   SYNTAX        CmaVbpModel
   MAX-ACCESS    read-only
   STATUS        current
   DESCRIPTION   "Model of the VBP device."
   ::= { cmaVbpStatusTableEntry 2 }

cmaVbpName         OBJECT-TYPE
   SYNTAX        OCTET STRING (SIZE(1..255))
   MAX-ACCESS    read-only
   STATUS        current
   DESCRIPTION   "Name of the VBP device."
   ::= { cmaVbpStatusTableEntry 3 }

cmaVbpLanInetAddressType         OBJECT-TYPE
   SYNTAX        InetAddressType
   MAX-ACCESS    read-only
   STATUS        current
   DESCRIPTION   "LAN IP address type of the VBP device."
   ::= { cmaVbpStatusTableEntry 4 }

cmaVbpLanInetAddress         OBJECT-TYPE
   SYNTAX        InetAddress
   MAX-ACCESS    read-only
   STATUS        current
   DESCRIPTION   "LAN IP address of the VBP device."
   ::= { cmaVbpStatusTableEntry 5 }

cmaVbpWanInetAddressType         OBJECT-TYPE
   SYNTAX        InetAddressType
   MAX-ACCESS    read-only
   STATUS        current
   DESCRIPTION   "WAN IP address type of the VBP device."
   ::= { cmaVbpStatusTableEntry 6 }

cmaVbpWanInetAddress         OBJECT-TYPE
   SYNTAX        InetAddress
   MAX-ACCESS    read-only
   STATUS        current
   DESCRIPTION   "WAN IP address of the VBP device."
   ::= { cmaVbpStatusTableEntry 7 }

-- END VBP status

-- START DMA status

cmaDmaCount OBJECT-TYPE
   SYNTAX       Integer32
   MAX-ACCESS   read-only
   STATUS       current
   DESCRIPTION  "Number of DMA systems known to the CMA server."
   ::= { cmaStatusDeviceDMA 1 }

CmaDmaStatusTableEntry ::= SEQUENCE
{
   cmaDmaIndex                          CmaDefaultTableIndexRange,
   cmaDmaName                           OCTET STRING,
   cmaDmaInetAddressType                InetAddressType,
   cmaDmaInetAddress                    InetAddress,
   cmaDmaStatus                         CmaDeviceStatus,
   cmaDmaIsCallServer                   TruthValue,
   cmaDmaIsConferenceManager            TruthValue,
   cmaDmaH323Enabled                    TruthValue,          
   cmaDmaSipEnabled                     TruthValue,
   cmaDmaSiteTopologyIntegrated         TruthValue
}

cmaDmaStatusTable      OBJECT-TYPE
   SYNTAX        SEQUENCE OF CmaDmaStatusTableEntry
   MAX-ACCESS    not-accessible
   STATUS        current
   DESCRIPTION   "DMA status table. Contains information 
                 about DMA systems."
   ::= { cmaStatusDeviceDMA 2 }

cmaDmaStatusTableEntry      OBJECT-TYPE
   SYNTAX        CmaDmaStatusTableEntry
   MAX-ACCESS    not-accessible
   STATUS        current
   DESCRIPTION   "DMA status table entry."
   INDEX         { cmaDmaIndex }
   ::= { cmaDmaStatusTable 1}

cmaDmaIndex         OBJECT-TYPE
   SYNTAX        CmaDefaultTableIndexRange
   MAX-ACCESS    read-only 
   STATUS        current
   DESCRIPTION   "Unique system-assigned ID for this entry." 
   ::= { cmaDmaStatusTableEntry 1 }

cmaDmaName         OBJECT-TYPE
   SYNTAX        OCTET STRING (SIZE(1..255))
   MAX-ACCESS    read-only
   STATUS        current
   DESCRIPTION   "Name of the DMA system."
   ::= { cmaDmaStatusTableEntry 2 }

cmaDmaInetAddressType         OBJECT-TYPE
   SYNTAX        InetAddressType
   MAX-ACCESS    read-only
   STATUS        current
   DESCRIPTION   "Host/IP address type of the DMA system."
   ::= { cmaDmaStatusTableEntry 3 }

cmaDmaInetAddress         OBJECT-TYPE
   SYNTAX        InetAddress
   MAX-ACCESS    read-only
   STATUS        current
   DESCRIPTION   "Host name or IP address of the DMA system."
   ::= { cmaDmaStatusTableEntry 4 }

cmaDmaStatus         OBJECT-TYPE
   SYNTAX        CmaDeviceStatus
   MAX-ACCESS    read-only
   STATUS        current
   DESCRIPTION   "Current status of the DMA system."
   ::= { cmaDmaStatusTableEntry 5 }

cmaDmaIsCallServer         OBJECT-TYPE
   SYNTAX        TruthValue
   MAX-ACCESS    read-only
   STATUS        current
   DESCRIPTION   "Flag indicating if the DMA is configured to be the Call Server for the system."
   ::= { cmaDmaStatusTableEntry 6 }

cmaDmaIsConferenceManager         OBJECT-TYPE
   SYNTAX        TruthValue
   MAX-ACCESS    read-only
   STATUS        current
   DESCRIPTION   "Flag indicating if the DMA is configured to be the conference manager for the system 
                  for anytime and pooled conferences."
   ::= { cmaDmaStatusTableEntry 7 }
   
cmaDmaH323Enabled         OBJECT-TYPE
   SYNTAX        TruthValue
   MAX-ACCESS    read-only
   STATUS        current
   DESCRIPTION   "Flag indicating if the DMA has H.323 signalling enabled."
   ::= { cmaDmaStatusTableEntry 8 }
   
cmaDmaSipEnabled         OBJECT-TYPE
   SYNTAX        TruthValue
   MAX-ACCESS    read-only
   STATUS        current
   DESCRIPTION   "Flag indicating if the DMA has SIP signalling enabled."
   ::= { cmaDmaStatusTableEntry 9 }
   
cmaDmaSiteTopologyIntegrated         OBJECT-TYPE
   SYNTAX        TruthValue
   MAX-ACCESS    read-only
   STATUS        current
   DESCRIPTION   "Flag indicating if the DMA is integrated with the XMA for site topology."
   ::= { cmaDmaStatusTableEntry 10 }
   
-- END DMA status 


-- START Peripheral status

cmaPeripheralCount OBJECT-TYPE
   SYNTAX       Integer32
   MAX-ACCESS   read-only
   STATUS       current
   DESCRIPTION  "Number of peripherals known to the CMA server."
   ::= { cmaStatusDevicePeripherals 1 }

CmaPeripheralStatusTableEntry ::= SEQUENCE
{
   cmaPeripheralIndex                      CmaDefaultTableIndexRange,
   cmaPeripheralPairedStatus               CmaPeripheralPairingStatus,
   cmaPeripheralAlertState                 CmaPeripheralAlertState,
   cmaPeripheralPairedName                 OCTET STRING,
   cmaPeripheralDeviceType                 CmaEndpointType,
   cmaPeripheralSerialNumber               OCTET STRING,
   cmaPeripheralInetAddress                InetAddress,
   cmaPeripheralInetAddressType            InetAddressType,
   cmaPeripheralHardwareVersion            OCTET STRING,   
   cmaPeripheralSoftwareVersion            OCTET STRING
}

cmaPeripheralStatusTable      OBJECT-TYPE
   SYNTAX        SEQUENCE OF CmaPeripheralStatusTableEntry
   MAX-ACCESS    not-accessible
   STATUS        current
   DESCRIPTION   "Peripheral status table. Contains information
                 about Peripherals."
   ::= { cmaStatusDevicePeripherals 2 }

cmaPeripheralStatusTableEntry      OBJECT-TYPE
   SYNTAX        CmaPeripheralStatusTableEntry
   MAX-ACCESS    not-accessible
   STATUS        current
   DESCRIPTION   "DMA status table entry."
   INDEX         { cmaPeripheralIndex }
   ::= { cmaPeripheralStatusTable 1}

cmaPeripheralIndex         OBJECT-TYPE
   SYNTAX        CmaDefaultTableIndexRange
   MAX-ACCESS    read-only
   STATUS        current
   DESCRIPTION   "Unique system-assigned ID for this entry."
   ::= { cmaPeripheralStatusTableEntry 1 }

cmaPeripheralPairedStatus         OBJECT-TYPE
   SYNTAX        CmaPeripheralPairingStatus
   MAX-ACCESS    read-only
   STATUS        current
   DESCRIPTION   "Current pairing status for the peripheral."
   ::= { cmaPeripheralStatusTableEntry 2 }

cmaPeripheralAlertState         OBJECT-TYPE
   SYNTAX        CmaPeripheralAlertState
   MAX-ACCESS    read-only
   STATUS        current
   DESCRIPTION   "Current error state for the peripheral."
   ::= { cmaPeripheralStatusTableEntry 3 }

cmaPeripheralPairedName         OBJECT-TYPE
   SYNTAX        OCTET STRING (SIZE(1..255))
   MAX-ACCESS    read-only
   STATUS        current
   DESCRIPTION   "Name of the paired HDX."
   ::= { cmaPeripheralStatusTableEntry 4 }

cmaPeripheralDeviceType         OBJECT-TYPE
   SYNTAX        CmaEndpointType
   MAX-ACCESS    read-only
   STATUS        current
   DESCRIPTION   "Device type for this peripheral."
   ::= { cmaPeripheralStatusTableEntry 5 }

cmaPeripheralSerialNumber         OBJECT-TYPE
   SYNTAX        OCTET STRING (SIZE(0..255))
   MAX-ACCESS    read-only
   STATUS        current
   DESCRIPTION   "Serial number for this peripheral."
   ::= { cmaPeripheralStatusTableEntry 6 }

cmaPeripheralInetAddress         OBJECT-TYPE
   SYNTAX        InetAddress
   MAX-ACCESS    read-only
   STATUS        current
   DESCRIPTION   "IP address of the peripheral."
   ::= { cmaPeripheralStatusTableEntry 7 }

cmaPeripheralInetAddressType         OBJECT-TYPE
   SYNTAX        InetAddressType
   MAX-ACCESS    read-only
   STATUS        current
   DESCRIPTION   "Inet address type for this peripheral."
   ::= { cmaPeripheralStatusTableEntry 8 }

cmaPeripheralHardwareVersion         OBJECT-TYPE
   SYNTAX        OCTET STRING (SIZE(0..255))
   MAX-ACCESS    read-only
   STATUS        current
   DESCRIPTION   "Hardware version for this peripheral."
   ::= { cmaPeripheralStatusTableEntry 9 }

cmaPeripheralSoftwareVersion         OBJECT-TYPE
   SYNTAX        OCTET STRING (SIZE(0..255))
   MAX-ACCESS    read-only
   STATUS        current
   DESCRIPTION   "Software version for this peripheral."
   ::= { cmaPeripheralStatusTableEntry 10 }

-- END Peripheral status

-- START RPAD status
cmaRpadCount OBJECT-TYPE
   SYNTAX       Integer32
   MAX-ACCESS   read-only
   STATUS       current
   DESCRIPTION  "Total number of RPADs known to the CMA server."
   ::= { cmaStatusDeviceRPAD 1 }

CmaRpadStatusTableEntry    ::= SEQUENCE
{
   cmaRpadIndex                  CmaDefaultTableIndexRange, 
   cmaRpadName                   OCTET STRING,
   cmaRpadStatus                 CmaDeviceStatus,
   cmaRpadProviderSideAddress    InetAddress,
   cmaRpadSiteName               OCTET STRING
}

cmaRpadStatusTable     OBJECT-TYPE
   SYNTAX       SEQUENCE OF CmaRpadStatusTableEntry
   MAX-ACCESS   not-accessible
   STATUS       current
   DESCRIPTION  "RPAD status table. Contains status, name,provider-side IP 
                 and site information for RPADs."
   ::= { cmaStatusDeviceRPAD 2 }

cmaRpadStatusTableEntry    OBJECT-TYPE
   SYNTAX       CmaRpadStatusTableEntry
   MAX-ACCESS   not-accessible
   STATUS       current
   DESCRIPTION  "RPAD status table entry."
   INDEX        { cmaRpadIndex }
   ::= { cmaRpadStatusTable 1 }

cmaRpadIndex     OBJECT-TYPE
   SYNTAX       CmaDefaultTableIndexRange 
   MAX-ACCESS   read-only 
   STATUS       current
   DESCRIPTION  "Unique system-assigned ID for this entry." 
   ::= { cmaRpadStatusTableEntry 1 }

cmaRpadName     OBJECT-TYPE
   SYNTAX       OCTET STRING (SIZE(1..255)) 
   MAX-ACCESS   read-only 
   STATUS       current
   DESCRIPTION  "Name of the RPAD."
   ::= { cmaRpadStatusTableEntry 2 }

cmaRpadStatus          OBJECT-TYPE
   SYNTAX       CmaDeviceStatus
   MAX-ACCESS   read-only 
   STATUS       current
   DESCRIPTION  "Status of the RPAD."
   ::= { cmaRpadStatusTableEntry 3 }

cmaRpadProviderSideAddress      OBJECT-TYPE
   SYNTAX       InetAddress
   MAX-ACCESS   read-only 
   STATUS       current
   DESCRIPTION  "Provider side IP address of the RPAD."
   ::= { cmaRpadStatusTableEntry 4 }

cmaRpadSiteName     OBJECT-TYPE
   SYNTAX       OCTET STRING (SIZE(1..255)) 
   MAX-ACCESS   read-only 
   STATUS       current
   DESCRIPTION  "Site Name of the RPAD."
   ::= { cmaRpadStatusTableEntry 5 }
-- END RPAD status

-- START SBC status
cmaSbcCount OBJECT-TYPE
   SYNTAX       Integer32
   MAX-ACCESS   read-only
   STATUS       current
   DESCRIPTION  "Number of SBCs known to the CMA server."
   ::= { cmaStatusDeviceSBC 1 }

CmaSbcStatusTableEntry ::= SEQUENCE
{
   cmaSbcIndex                           CmaDefaultTableIndexRange,
   cmaSbcName                            OCTET STRING,
   cmaSbcLanInetAddressType     InetAddressType,
   cmaSbcLanInetAddress         InetAddress,
   cmaSbcWanInetAddressType   InetAddressType,
   cmaSbcWanInetAddress       InetAddress       
}

cmaSbcStatusTable      OBJECT-TYPE
   SYNTAX        SEQUENCE OF CmaSbcStatusTableEntry
   MAX-ACCESS    not-accessible
   STATUS        current
   DESCRIPTION   "SBC status table. Contains information about 
                  Polycom Video Border Proxy devices."
   ::= { cmaStatusDeviceSBC 2 }

cmaSbcStatusTableEntry      OBJECT-TYPE
   SYNTAX        CmaSbcStatusTableEntry
   MAX-ACCESS    not-accessible
   STATUS        current
   DESCRIPTION   "SBC status table entry."
   INDEX         { cmaSbcIndex }
   ::= { cmaSbcStatusTable 1}

cmaSbcIndex         OBJECT-TYPE
   SYNTAX        CmaDefaultTableIndexRange
   MAX-ACCESS    read-only
   STATUS        current
   DESCRIPTION   "Unique system-assigned ID for this entry." 
   ::= { cmaSbcStatusTableEntry 1 }


cmaSbcName         OBJECT-TYPE
   SYNTAX        OCTET STRING (SIZE(1..255))
   MAX-ACCESS    read-only
   STATUS        current
   DESCRIPTION   "Name of the SBC device."
   ::= { cmaSbcStatusTableEntry 3 }

cmaSbcLanInetAddressType         OBJECT-TYPE
   SYNTAX        InetAddressType
   MAX-ACCESS    read-only
   STATUS        current
   DESCRIPTION   "LAN IP address type of the SBC device."
   ::= { cmaSbcStatusTableEntry 4 }

cmaSbcLanInetAddress         OBJECT-TYPE
   SYNTAX        InetAddress
   MAX-ACCESS    read-only
   STATUS        current
   DESCRIPTION   "LAN IP address of the SBC device."
   ::= { cmaSbcStatusTableEntry 5 }

cmaSbcWanInetAddressType         OBJECT-TYPE
   SYNTAX        InetAddressType
   MAX-ACCESS    read-only
   STATUS        current
   DESCRIPTION   "WAN IP address type of the SBC device."
   ::= { cmaSbcStatusTableEntry 6 }

cmaSbcWanInetAddress         OBJECT-TYPE
   SYNTAX        InetAddress
   MAX-ACCESS    read-only
   STATUS        current
   DESCRIPTION   "WAN IP address of the SBC device."
   ::= { cmaSbcStatusTableEntry 7 }

-- END SBC status

-- START Conference summary
cmaStatusConferenceGroup OBJECT-GROUP 
   OBJECTS
   {
      cmaConfSummaryCompletedScheduledCount,
      cmaConfSummaryActiveScheduledCount,
      cmaConfSummaryFutureScheduledCount,
      cmaConfSummaryCompletedAdhocCount,
      cmaConfSummaryActiveAdhocCount,
      cmaActiveConferenceCount,
      cmaConferenceIndex,
      cmaConferenceName,
      cmaConferenceScheduleId,
      cmaConferenceType,
      cmaConferenceIsScheduled,
      cmaConferenceIsRecurring,
      cmaConferenceStartTime,
      cmaConferenceOwner,
      cmaConferenceStatus,
      cmaConferenceTotalParticipants,
      cmaConferenceConnectedParticipants,
      cmaConferenceIsCascaded,
      cmaConferenceMcu,
      cmaConferenceAvgParticipantAudioQOE,
      cmaConferenceAvgParticipantVideoQOE,
      cmaConferenceAvgParticipantContentQOE,
      cmaConferenceMinParticipantAudioQOE,
      cmaConferenceMinParticipantVideoQOE,
      cmaConferenceMinParticipantContentQOE
    
   }
   STATUS current
   DESCRIPTION "CMA conference status conformance group."
   ::= { cmaStatusConformance 8 }

cmaConfSummaryCompletedScheduledCount        OBJECT-TYPE
   SYNTAX        Integer32
   MAX-ACCESS    read-only
   STATUS        current
   DESCRIPTION   "Number of completed scheduled conferences since midnight."
   ::= { cmaStatusConferenceSummary 1 }

cmaConfSummaryActiveScheduledCount        OBJECT-TYPE
   SYNTAX        Integer32
   MAX-ACCESS    read-only
   STATUS        current
   DESCRIPTION   "Number of active scheduled conferences."
   ::= { cmaStatusConferenceSummary 2 }

cmaConfSummaryFutureScheduledCount        OBJECT-TYPE
   SYNTAX        Integer32
   MAX-ACCESS    read-only
   STATUS        current
   DESCRIPTION   "Number of future scheduled conferences for today
                  (i.e., until midnight of the current day)."
   ::= { cmaStatusConferenceSummary 3 }

cmaConfSummaryCompletedAdhocCount        OBJECT-TYPE
   SYNTAX        Integer32
   MAX-ACCESS    read-only
   STATUS        current
   DESCRIPTION   "Number of completed ad hoc conferences since midnight."
   ::= { cmaStatusConferenceSummary 4 }

cmaConfSummaryActiveAdhocCount        OBJECT-TYPE
   SYNTAX        Integer32
   MAX-ACCESS    read-only
   STATUS        current
   DESCRIPTION   "Number of active ad hoc conferences."
   ::= { cmaStatusConferenceSummary 5 }

-- END Conference summary

-- START Conference status 

cmaActiveConferenceCount        OBJECT-TYPE
   SYNTAX        Integer32
   MAX-ACCESS    read-only
   STATUS        current
   DESCRIPTION   "Total number of active conferences (both scheduled and ad hoc)"
   ::= { cmaStatusConferencesOngoing 1 }

CmaActiveConferenceTableEntry   ::= SEQUENCE
{
   cmaConferenceIndex                             CmaDefaultTableIndexRange,
   cmaConferenceName                              OCTET STRING,
   cmaConferenceScheduleId                        OCTET STRING,
   cmaConferenceType                              CmaConferenceType, 
   cmaConferenceIsScheduled                       TruthValue,
   cmaConferenceIsRecurring                       TruthValue,
   cmaConferenceStartTime                         DateAndTime,
   cmaConferenceOwner                             OCTET STRING,
   cmaConferenceStatus                            CmaConferenceStatus,
   cmaConferenceTotalParticipants                 Integer32,
   cmaConferenceConnectedParticipants             Integer32,
   cmaConferenceIsCascaded                        TruthValue,
   cmaConferenceMcu                               OCTET STRING,
   cmaConferenceAvgParticipantAudioQOE            Integer32,
   cmaConferenceAvgParticipantVideoQOE            Integer32,
   cmaConferenceAvgParticipantContentQOE          Integer32,
   cmaConferenceMinParticipantAudioQOE            Integer32,
   cmaConferenceMinParticipantVideoQOE            Integer32,
   cmaConferenceMinParticipantContentQOE          Integer32
   
}

cmaActiveConferenceTable     OBJECT-TYPE
   SYNTAX        SEQUENCE OF CmaActiveConferenceTableEntry
   MAX-ACCESS    not-accessible
   STATUS        current
   DESCRIPTION   "Active conference table. Contains the available 
                  information for all active conferences."
   ::= { cmaStatusConferencesOngoing 2 }

cmaActiveConferenceTableEntry      OBJECT-TYPE
   SYNTAX        CmaActiveConferenceTableEntry
   MAX-ACCESS    not-accessible
   STATUS        current
   DESCRIPTION   "Active conference table entry."
   INDEX         { cmaConferenceIndex }
   ::= { cmaActiveConferenceTable 1 }

cmaConferenceIndex         OBJECT-TYPE
   SYNTAX        CmaDefaultTableIndexRange
   MAX-ACCESS    read-only
   STATUS        current
   DESCRIPTION   "Unique system-assigned ID for this entry." 
   ::= { cmaActiveConferenceTableEntry 1 }

cmaConferenceName         OBJECT-TYPE
   SYNTAX        OCTET STRING (SIZE(1..255))
   MAX-ACCESS    read-only
   STATUS        current
   DESCRIPTION   "Name of the conference."
   ::= { cmaActiveConferenceTableEntry 2 }

cmaConferenceScheduleId         OBJECT-TYPE
   SYNTAX        OCTET STRING (SIZE(1..255))
   MAX-ACCESS    read-only
   STATUS        current
   DESCRIPTION   "Scheduling ID of the conference."
   ::= { cmaActiveConferenceTableEntry 3 }

cmaConferenceType         OBJECT-TYPE
   SYNTAX        CmaConferenceType
   MAX-ACCESS    read-only
   STATUS        current
   DESCRIPTION   "Type (audio-only or video) of the conference."
   ::= { cmaActiveConferenceTableEntry 4 }

cmaConferenceIsScheduled         OBJECT-TYPE
   SYNTAX        TruthValue
   MAX-ACCESS    read-only
   STATUS        current
   DESCRIPTION   "Flag indicating whether the conference is scheduled (true)
                  or ad hoc (false)."
   ::= { cmaActiveConferenceTableEntry 5 }

cmaConferenceIsRecurring         OBJECT-TYPE
   SYNTAX        TruthValue
   MAX-ACCESS    read-only
   STATUS        current
   DESCRIPTION   "Flag indicating whether the conference is a recurring conference."
   ::= { cmaActiveConferenceTableEntry 6 }

cmaConferenceStartTime         OBJECT-TYPE
   SYNTAX        DateAndTime
   MAX-ACCESS    read-only
   STATUS        current
   DESCRIPTION   "Start date/time of the conference."
   ::= { cmaActiveConferenceTableEntry 7 }

cmaConferenceOwner         OBJECT-TYPE
   SYNTAX        OCTET STRING (SIZE(0..255))
   MAX-ACCESS    read-only
   STATUS        current
   DESCRIPTION   "Owner of the conference."
   ::= { cmaActiveConferenceTableEntry 8 }

cmaConferenceStatus         OBJECT-TYPE
   SYNTAX        CmaConferenceStatus
   MAX-ACCESS    read-only
   STATUS        current
   DESCRIPTION   "Status of the conference."
   ::= { cmaActiveConferenceTableEntry 9 }

cmaConferenceTotalParticipants         OBJECT-TYPE
   SYNTAX        Integer32
   MAX-ACCESS    read-only
   STATUS        current
   DESCRIPTION   "Total number of participants for the conference (both connected 
                  and disconnected)."
   ::= { cmaActiveConferenceTableEntry 10 }

cmaConferenceConnectedParticipants         OBJECT-TYPE
   SYNTAX        Integer32
   MAX-ACCESS    read-only
   STATUS        current
   DESCRIPTION   "Number of connected participants for the conference."
   ::= { cmaActiveConferenceTableEntry 11 }

cmaConferenceIsCascaded         OBJECT-TYPE
   SYNTAX        TruthValue
   MAX-ACCESS    read-only
   STATUS        current
   DESCRIPTION   "Flag indicating whether the conference is cascaded."
   ::= { cmaActiveConferenceTableEntry 12 }

cmaConferenceMcu         OBJECT-TYPE
   SYNTAX        OCTET STRING (SIZE(0..255))
   MAX-ACCESS    read-only
   STATUS        current
   DESCRIPTION   "Name of the MCU hosting the conference. Empty if no MCU is involved. 
                  For cascaded conferences, this is a comma-delimited list of MCUs."
   ::= { cmaActiveConferenceTableEntry 13 }

cmaConferenceAvgParticipantAudioQOE         OBJECT-TYPE
   SYNTAX        Integer32          -- meaning is yet to be defined
   MAX-ACCESS    read-only
   STATUS        current
   DESCRIPTION   "Average audio QOE (Quality Of Experience)
                  for all connected participants in the conference."
   ::= { cmaActiveConferenceTableEntry 14 }

cmaConferenceAvgParticipantVideoQOE         OBJECT-TYPE
   SYNTAX        Integer32          -- meaning is yet to be defined
   MAX-ACCESS    read-only
   STATUS        current
   DESCRIPTION   "Average video QOE (Quality Of Experience)
                  for all connected participants in the conference."
   ::= { cmaActiveConferenceTableEntry 15 }

cmaConferenceAvgParticipantContentQOE         OBJECT-TYPE
   SYNTAX        Integer32          -- meaning is yet to be defined
   MAX-ACCESS    read-only
   STATUS        current
   DESCRIPTION   "Average content QOE (Quality Of Experience)
                  for all connected participants in the conference."
   ::= { cmaActiveConferenceTableEntry 16 }

cmaConferenceMinParticipantAudioQOE         OBJECT-TYPE
   SYNTAX        Integer32          -- meaning is yet to be defined
   MAX-ACCESS    read-only
   STATUS        current
   DESCRIPTION   "Minimum audio QOE (Quality Of Experience) across 
                  all connected participants in the conference."
   ::= { cmaActiveConferenceTableEntry 17 }

cmaConferenceMinParticipantVideoQOE         OBJECT-TYPE
   SYNTAX        Integer32          -- meaning is yet to be defined
   MAX-ACCESS    read-only
   STATUS        current
   DESCRIPTION   "Minimum video QOE (Quality Of Experience) across 
                  all connected participants in the conference."
   ::= { cmaActiveConferenceTableEntry 18 }

cmaConferenceMinParticipantContentQOE         OBJECT-TYPE
   SYNTAX        Integer32          -- meaning is yet to be defined
   MAX-ACCESS    read-only
   STATUS        current
   DESCRIPTION   "Minimum content QOE (Quality Of Experience) across 
                  all connected participants in the conference."
   ::= { cmaActiveConferenceTableEntry 19 }

-- END Conference status 

-- START system alerts
cmaStatusSystemAlertGroup OBJECT-GROUP 
   OBJECTS
   {
      cmaSystemAlertCount,
      cmaSystemAlertIndex,
      cmaSystemAlertSequenceNumber,
      cmaSystemAlertType,
      cmaSystemAlertDescription,
      cmaSystemAlertGenerationTime,
      cmaSystemAlertNotes
   }
   STATUS current
   DESCRIPTION "CMA system alerts status conformance group."
   ::= { cmaStatusConformance 9 }

cmaSystemAlertCount        OBJECT-TYPE
   SYNTAX        Integer32
   MAX-ACCESS    read-only
   STATUS        current
   DESCRIPTION   "Number of active system alerts."
   ::= { cmaStatusAlerts 1 }

CmaSystemAlertTableEntry   ::= SEQUENCE
{
   cmaSystemAlertIndex           CmaDefaultTableIndexRange,
   cmaSystemAlertSequenceNumber  Counter32,
   cmaSystemAlertType            CmaSystemAlertType,
   cmaSystemAlertDescription     OCTET STRING,
   cmaSystemAlertGenerationTime  DateAndTime,
   cmaSystemAlertNotes           OCTET STRING
}

cmaSystemAlertTable     OBJECT-TYPE
   SYNTAX        SEQUENCE OF CmaSystemAlertTableEntry
   MAX-ACCESS    not-accessible
   STATUS        current
   DESCRIPTION   "System alert table. Contains information for all 
                  active alerts."
   ::= { cmaStatusAlerts 2 }

cmaSystemAlertTableEntry      OBJECT-TYPE
   SYNTAX        CmaSystemAlertTableEntry
   MAX-ACCESS    not-accessible
   STATUS        current
   DESCRIPTION   "System alert table entry."
   INDEX         { cmaSystemAlertIndex }
   ::= { cmaSystemAlertTable 1 }

cmaSystemAlertIndex         OBJECT-TYPE
   SYNTAX        CmaDefaultTableIndexRange
   MAX-ACCESS    read-only
   STATUS        current
   DESCRIPTION   "Unique system-assigned ID for this entry." 
   ::= { cmaSystemAlertTableEntry 1 }

cmaSystemAlertSequenceNumber         OBJECT-TYPE
   SYNTAX        Counter32
   MAX-ACCESS    read-only
   STATUS        current
   DESCRIPTION   "Sequence number of the system alert."
   ::= { cmaSystemAlertTableEntry 2 }

cmaSystemAlertType         OBJECT-TYPE
   SYNTAX        CmaSystemAlertType
   MAX-ACCESS    read-only
   STATUS        current
   DESCRIPTION   "Alert type of the system alert."
   ::= { cmaSystemAlertTableEntry 3 }

cmaSystemAlertDescription         OBJECT-TYPE
   SYNTAX        OCTET STRING
   MAX-ACCESS    read-only
   STATUS        current
   DESCRIPTION   "Description of the system alert."
   ::= { cmaSystemAlertTableEntry 4 }

cmaSystemAlertGenerationTime         OBJECT-TYPE
   SYNTAX        DateAndTime
   MAX-ACCESS    read-only
   STATUS        current
   DESCRIPTION   "Date and time when the system alert was generated."
   ::= { cmaSystemAlertTableEntry 5 }

cmaSystemAlertNotes         OBJECT-TYPE
   SYNTAX        OCTET STRING
   MAX-ACCESS    read-only
   STATUS        current
   DESCRIPTION   "Notes for the system alert."
   ::= { cmaSystemAlertTableEntry 6 }

-- END system alerts

-- START Redundancy status
cmaStatusRedundancyGroup OBJECT-GROUP 
   OBJECTS
   {
      cmaRedundancyStatus,
      cmaRedundancyVirtualInetAddressType,
      cmaRedundancyVirtualInetAddress,
      cmaRedundantServerIndex,
      cmaRedundantServerInetAddressType,
      cmaRedundantServerInetAddress,
      cmaRedundantServerRole,
      cmaRedundantServerMachineStatus
   }
   STATUS current
   DESCRIPTION "CMA redundancy status conformance group."
   ::= { cmaStatusConformance 10 }

cmaRedundancyStatus         OBJECT-TYPE
   SYNTAX        RedundancyStatusType
   MAX-ACCESS    read-only
   STATUS        current
   DESCRIPTION   "CMA server redundancy status (no redundancy, 
                  redundancy OK, or redundancy with error)."
   ::= { cmaStatusRedundancy 1 }

cmaRedundancyVirtualInetAddressType         OBJECT-TYPE
   SYNTAX        InetAddressType
   MAX-ACCESS    read-only
   STATUS        current
   DESCRIPTION   "Virtual IP address type of the CMA system 
                  (valid only if redundancy is enabled)."
   ::= { cmaStatusRedundancy 2 }

cmaRedundancyVirtualInetAddress             OBJECT-TYPE
   SYNTAX        InetAddress
   MAX-ACCESS    read-only
   STATUS        current
   DESCRIPTION   "Virtual IP address of the CMA system
                  (valid only if redundancy is enabled)."
   ::= { cmaStatusRedundancy 3 }

CmaRedundancyTableEntry   ::= SEQUENCE
{
   cmaRedundantServerIndex              CmaDefaultTableIndexRange,
   cmaRedundantServerInetAddressType    InetAddressType,
   cmaRedundantServerInetAddress        InetAddress,
   cmaRedundantServerRole               CmaRedundantServerRole, 
   cmaRedundantServerMachineStatus      CmaRedundantServerStatus
}

cmaRedundancyTable     OBJECT-TYPE
   SYNTAX        SEQUENCE OF CmaRedundancyTableEntry
   MAX-ACCESS    not-accessible
   STATUS        current
   DESCRIPTION   "CMA server redundancy table. In a redundant system, it 
                  includes an entry for each of the two servers."
   ::= { cmaStatusRedundancy 4 }

cmaRedundancyTableEntry      OBJECT-TYPE
   SYNTAX        CmaRedundancyTableEntry
   MAX-ACCESS    not-accessible
   STATUS        current
   DESCRIPTION   "CMA server redundancy table entry."
   INDEX         { cmaRedundantServerIndex }
   ::= { cmaRedundancyTable 1 }

cmaRedundantServerIndex         OBJECT-TYPE
   SYNTAX        CmaDefaultTableIndexRange
   MAX-ACCESS    read-only
   STATUS        current
   DESCRIPTION   "Unique system-assigned ID for this entry." 
   ::= { cmaRedundancyTableEntry 1 }

cmaRedundantServerInetAddressType         OBJECT-TYPE
   SYNTAX        InetAddressType
   MAX-ACCESS    read-only
   STATUS        current
   DESCRIPTION   "IP address type of the server."
   ::= { cmaRedundancyTableEntry 2 }

cmaRedundantServerInetAddress         OBJECT-TYPE
   SYNTAX        InetAddress
   MAX-ACCESS    read-only
   STATUS        current
   DESCRIPTION   "IP address of the server."
   ::= { cmaRedundancyTableEntry 3 }

cmaRedundantServerRole         OBJECT-TYPE
   SYNTAX        CmaRedundantServerRole
   MAX-ACCESS    read-only
   STATUS        current
   DESCRIPTION   "Role of the server."
   ::= { cmaRedundancyTableEntry 4 }

cmaRedundantServerMachineStatus         OBJECT-TYPE
   SYNTAX        CmaRedundantServerStatus
   MAX-ACCESS    read-only
   STATUS        current
   DESCRIPTION   "Machine status of the server."
   ::= { cmaRedundancyTableEntry 6 }

-- END Redundancy status

-- START Site statistics

cmaStatusSitesGroup OBJECT-GROUP 
   OBJECTS
   {
      cmaSiteCount,
      cmaSiteIndex,
      cmaSiteName,
      cmaSiteCallCount,
      cmaSiteBandwidthUsed,
      cmaSiteBandwidthTotal,
      cmaSiteAverageCallBitRate,
      cmaSitePacketLoss,
      cmaSiteAverageJitter,
      cmaSiteAverageDelay,
      cmaSiteLinkCount,
      cmaSiteLinkIndex,
      cmaSiteLinkName,
      cmaSiteLinkFromSite,
      cmaSiteLinkToSite,
      cmaSiteLinkCallCount,
      cmaSiteLinkBandwidthUsed,
      cmaSiteLinkBandwidthTotal,
      cmaSiteLinkAverageCallBitRate,
      cmaSiteLinkPacketLoss,
      cmaSiteLinkAverageJitter,
      cmaSiteLinkAverageDelay,
      cmaSubnetCount,
      cmaSubnetIndex,
      cmaSubnetName,
      cmaSubnetSiteName,
      cmaSubnetCallCount,
      cmaSubnetBandwidthUsed,
      cmaSubnetBandwidthTotal,
      cmaSubnetAverageCallBitRate,
      cmaSubnetPacketLoss,
      cmaSubnetAverageJitter,
      cmaSubnetAverageDelay
   }
   STATUS current
   DESCRIPTION "CMA sites status conformance group."
   ::= { cmaStatusConformance 11 }

cmaSiteCount        OBJECT-TYPE
   SYNTAX        Integer32
   MAX-ACCESS    read-only
   STATUS        current
   DESCRIPTION   "Number of sites provisioned in the CMA server."
   ::= { cmaStatusSites 1 }

CmaSiteTableEntry   ::= SEQUENCE
{
   cmaSiteIndex                CmaDefaultTableIndexRange,
   cmaSiteName                 OCTET STRING,
   cmaSiteCallCount            Integer32,
   cmaSiteBandwidthUsed        Integer32,
   cmaSiteBandwidthTotal       Counter64,
   cmaSiteAverageCallBitRate   Counter64,
   cmaSitePacketLoss           Integer32,
   cmaSiteAverageJitter        Integer32,
   cmaSiteAverageDelay         Integer32
}

cmaSiteTable     OBJECT-TYPE
   SYNTAX        SEQUENCE OF CmaSiteTableEntry
   MAX-ACCESS    not-accessible
   STATUS        current
   DESCRIPTION   "CMA site table. Contains usage and network quality 
                  information for the sites.  Only CMA controlled
                  sites will be included in this table."
   ::= { cmaStatusSites 2 }

cmaSiteTableEntry      OBJECT-TYPE
   SYNTAX        CmaSiteTableEntry
   MAX-ACCESS    not-accessible
   STATUS        current
   DESCRIPTION   "CMA site table entry."
   INDEX         { cmaSiteIndex }
   ::= { cmaSiteTable 1 }

cmaSiteIndex         OBJECT-TYPE
   SYNTAX        CmaDefaultTableIndexRange
   MAX-ACCESS    read-only
   STATUS        current
   DESCRIPTION   "Unique system-assigned ID for this entry."
   ::= { cmaSiteTableEntry 1 }

cmaSiteName         OBJECT-TYPE
   SYNTAX        OCTET STRING (SIZE(1..255))
   MAX-ACCESS    read-only
   STATUS        current
   DESCRIPTION   "Name of the site."
   ::= { cmaSiteTableEntry 2 }

cmaSiteCallCount         OBJECT-TYPE
   SYNTAX        Integer32
   MAX-ACCESS    read-only
   STATUS        current
   DESCRIPTION   "Number of active calls in the site."
   ::= { cmaSiteTableEntry 3 }

cmaSiteBandwidthUsed         OBJECT-TYPE
   SYNTAX        Integer32 (0..100)
   MAX-ACCESS    read-only
   STATUS        current
   DESCRIPTION   "Percentage of bandwidth used in the site."
   ::= { cmaSiteTableEntry 4 }

cmaSiteBandwidthTotal         OBJECT-TYPE
   SYNTAX        Counter64
   MAX-ACCESS    read-only
   STATUS        current
   DESCRIPTION   "Total bandwidth used in the site."
   ::= { cmaSiteTableEntry 5 }

cmaSiteAverageCallBitRate     OBJECT-TYPE
   SYNTAX        Counter64
   MAX-ACCESS    read-only
   STATUS        current
   DESCRIPTION   "Average call bit rate in the site."
   ::= { cmaSiteTableEntry 6 }

cmaSitePacketLoss         OBJECT-TYPE
   SYNTAX        Integer32 (0..100)
   MAX-ACCESS    read-only
   STATUS        current
   DESCRIPTION   "Percentage of packet loss in the site."
   ::= { cmaSiteTableEntry 7 }

cmaSiteAverageJitter         OBJECT-TYPE
   SYNTAX        Integer32
   MAX-ACCESS    read-only
   STATUS        current
   DESCRIPTION   "Average jitter in the site."
   ::= { cmaSiteTableEntry 8 }
   
cmaSiteAverageDelay         OBJECT-TYPE
   SYNTAX        Integer32
   MAX-ACCESS    read-only
   STATUS        current
   DESCRIPTION   "Average delay in the site."
   ::= { cmaSiteTableEntry 9 }


-- END Site statistics

-- START Site link statistics

cmaSiteLinkCount        OBJECT-TYPE
   SYNTAX        Integer32
   MAX-ACCESS    read-only
   STATUS        current
   DESCRIPTION   "Number of site links provisioned in the CMA server."
   ::= { cmaStatusSiteLinks 1 }

CmaSiteLinkTableEntry   ::= SEQUENCE
{
   cmaSiteLinkIndex              CmaDefaultTableIndexRange,
   cmaSiteLinkName               OCTET STRING,
   cmaSiteLinkFromSite           OCTET STRING,
   cmaSiteLinkToSite             OCTET STRING, 
   cmaSiteLinkCallCount          Integer32,
   cmaSiteLinkBandwidthUsed      Integer32,
   cmaSiteLinkBandwidthTotal     Counter64,
   cmaSiteLinkAverageCallBitRate Counter64,
   cmaSiteLinkPacketLoss         Integer32,
   cmaSiteLinkAverageJitter      Integer32,
   cmaSiteLinkAverageDelay       Integer32
}

cmaSiteLinkTable     OBJECT-TYPE
   SYNTAX        SEQUENCE OF CmaSiteLinkTableEntry
   MAX-ACCESS    not-accessible
   STATUS        current
   DESCRIPTION   "CMA site link table. Contains usage and network 
                  quality information for the site links.  Only site links
                  with at least one CMA controlled site will be included
                  in this table"
   ::= { cmaStatusSiteLinks 2 }

cmaSiteLinkTableEntry      OBJECT-TYPE
   SYNTAX        CmaSiteLinkTableEntry
   MAX-ACCESS    not-accessible
   STATUS        current
   DESCRIPTION   "CMA site link table entry."
   INDEX         { cmaSiteLinkIndex }
   ::= { cmaSiteLinkTable 1 }

cmaSiteLinkIndex         OBJECT-TYPE
   SYNTAX        CmaDefaultTableIndexRange
   MAX-ACCESS    read-only
   STATUS        current
   DESCRIPTION   "Unique system-assigned ID for this entry."
   ::= { cmaSiteLinkTableEntry 1 }

cmaSiteLinkName         OBJECT-TYPE
   SYNTAX        OCTET STRING (SIZE(1..255))
   MAX-ACCESS    read-only
   STATUS        current
   DESCRIPTION   "Name of the site link."
   ::= { cmaSiteLinkTableEntry 2 }

cmaSiteLinkFromSite         OBJECT-TYPE
   SYNTAX        OCTET STRING (SIZE(1..255))
   MAX-ACCESS    read-only
   STATUS        current
   DESCRIPTION   "Name of the site of origin for the link."
   ::= { cmaSiteLinkTableEntry 3 }

cmaSiteLinkToSite         OBJECT-TYPE
   SYNTAX        OCTET STRING (SIZE(1..255))
   MAX-ACCESS    read-only
   STATUS        current
   DESCRIPTION   "Name of the destination site for the link."
   ::= { cmaSiteLinkTableEntry 4 }

cmaSiteLinkCallCount         OBJECT-TYPE
   SYNTAX        Integer32
   MAX-ACCESS    read-only
   STATUS        current
   DESCRIPTION   "Number of active calls in the link."
   ::= { cmaSiteLinkTableEntry 5 }

cmaSiteLinkBandwidthUsed         OBJECT-TYPE
   SYNTAX        Integer32 (0..100)
   MAX-ACCESS    read-only
   STATUS        current
   DESCRIPTION   "Percentage of bandwidth used in the link."
   ::= { cmaSiteLinkTableEntry 6 }

cmaSiteLinkBandwidthTotal         OBJECT-TYPE
   SYNTAX        Counter64
   MAX-ACCESS    read-only
   STATUS        current
   DESCRIPTION   "Total bandwidth used in the link."
   ::= { cmaSiteLinkTableEntry 7 }

cmaSiteLinkAverageCallBitRate         OBJECT-TYPE
   SYNTAX        Counter64
   MAX-ACCESS    read-only
   STATUS        current
   DESCRIPTION   "Average call bit rate in the link."
   ::= { cmaSiteLinkTableEntry 8 }

cmaSiteLinkPacketLoss         OBJECT-TYPE
   SYNTAX        Integer32 (0..100)
   MAX-ACCESS    read-only
   STATUS        current
   DESCRIPTION   "Percentage of packet loss in the link."
   ::= { cmaSiteLinkTableEntry 9 }

cmaSiteLinkAverageJitter         OBJECT-TYPE
   SYNTAX        Integer32
   MAX-ACCESS    read-only
   STATUS        current
   DESCRIPTION   "Average jitter in the link."
   ::= { cmaSiteLinkTableEntry 10}

cmaSiteLinkAverageDelay         OBJECT-TYPE
   SYNTAX        Integer32
   MAX-ACCESS    read-only
   STATUS        current
   DESCRIPTION   "Average delay in the link."
   ::= { cmaSiteLinkTableEntry 11 }

-- END Site link statistics

-- START Subnet statistics

cmaSubnetCount        OBJECT-TYPE
   SYNTAX        Integer32
   MAX-ACCESS    read-only
   STATUS        current
   DESCRIPTION   "Number of subnets provisioned in the CMA server."
   ::= { cmaStatusSubnets 1 }

CmaSubnetTableEntry   ::= SEQUENCE
{
   cmaSubnetIndex              CmaDefaultTableIndexRange,
   cmaSubnetName               OCTET STRING,
   cmaSubnetSiteName           OCTET STRING,
   cmaSubnetCallCount          Integer32,
   cmaSubnetBandwidthUsed      Integer32,
   cmaSubnetBandwidthTotal     Counter64,
   cmaSubnetAverageCallBitRate Counter64,
   cmaSubnetPacketLoss         Integer32,
   cmaSubnetAverageJitter      Integer32,
   cmaSubnetAverageDelay       Integer32
}

cmaSubnetTable     OBJECT-TYPE
   SYNTAX        SEQUENCE OF CmaSubnetTableEntry
   MAX-ACCESS    not-accessible
   STATUS        current
   DESCRIPTION   "CMA subnet table. Contains usage and network quality 
                  information for the Subnets.  Only subnets that are 
                  contained within CMA controlled sites will be included
                  in this table."
   ::= { cmaStatusSubnets 2 }

cmaSubnetTableEntry      OBJECT-TYPE
   SYNTAX        CmaSubnetTableEntry
   MAX-ACCESS    not-accessible
   STATUS        current
   DESCRIPTION   "CMA subnet table entry."
   INDEX         { cmaSubnetIndex }
   ::= { cmaSubnetTable 1 }

cmaSubnetIndex         OBJECT-TYPE
   SYNTAX        CmaDefaultTableIndexRange
   MAX-ACCESS    read-only
   STATUS        current
   DESCRIPTION   "Unique system-assigned ID for this entry."
   ::= { cmaSubnetTableEntry 1 }

cmaSubnetName         OBJECT-TYPE
   SYNTAX        OCTET STRING (SIZE(1..255))
   MAX-ACCESS    read-only
   STATUS        current
   DESCRIPTION   "Name of the subnet."
   ::= { cmaSubnetTableEntry 2 }

cmaSubnetSiteName         OBJECT-TYPE
   SYNTAX        OCTET STRING (SIZE(1..255))
   MAX-ACCESS    read-only
   STATUS        current
   DESCRIPTION   "Name of the subnet's site."
   ::= { cmaSubnetTableEntry 3 }

cmaSubnetCallCount         OBJECT-TYPE
   SYNTAX        Integer32
   MAX-ACCESS    read-only
   STATUS        current
   DESCRIPTION   "Number of active calls in the subnet."
   ::= { cmaSubnetTableEntry 4 }

cmaSubnetBandwidthUsed         OBJECT-TYPE
   SYNTAX        Integer32 (0..100)
   MAX-ACCESS    read-only
   STATUS        current
   DESCRIPTION   "Percentage of bandwidth used in the Subnet."
   ::= { cmaSubnetTableEntry 5 }

cmaSubnetBandwidthTotal         OBJECT-TYPE
   SYNTAX        Counter64
   MAX-ACCESS    read-only
   STATUS        current
   DESCRIPTION   "Total bandwidth used in the subnet."
   ::= { cmaSubnetTableEntry 6 }

cmaSubnetAverageCallBitRate     OBJECT-TYPE
   SYNTAX        Counter64
   MAX-ACCESS    read-only
   STATUS        current
   DESCRIPTION   "Average call bit rate in the subnet."
   ::= { cmaSubnetTableEntry 7 }

cmaSubnetPacketLoss         OBJECT-TYPE
   SYNTAX        Integer32 (0..100)
   MAX-ACCESS    read-only
   STATUS        current
   DESCRIPTION   "Percentage of packet loss in the subnet."
   ::= { cmaSubnetTableEntry 8 }

cmaSubnetAverageJitter         OBJECT-TYPE
   SYNTAX        Integer32
   MAX-ACCESS    read-only
   STATUS        current
   DESCRIPTION   "Average jitter in the subnet."
   ::= { cmaSubnetTableEntry 9 }

cmaSubnetAverageDelay         OBJECT-TYPE
   SYNTAX        Integer32
   MAX-ACCESS    read-only
   STATUS        current
   DESCRIPTION   "Average delay in the subnet."
   ::= { cmaSubnetTableEntry 10 }

-- END Subnet statistics

-------------------------------------------------------------------------------
-- Alert Group
-------------------------------------------------------------------------------
alertGroup OBJECT-GROUP
   OBJECTS 
   {
      alertSequenceNumber,
      alertSeverity,
      alertTimeStamp,
      alertFailedServerInetAddressType,
      alertFailedServerInetAddress,
      alertActiveServerInetAddressType,
      alertActiveServerInetAddress,
      alertRedundantServerInetAddressType,
      alertRedundantServerInetAddress,
      alertCmaServerInetAddressType,
      alertCmaServerInetAddress,
      alertMcuName,
      alertCmaDbName,
      alertSiteName,
      alertSubnetInetAddressType,
      alertSubnetInetAddress,
      alertSubnetMask,
      alertSiteLinkName,
      alertBandwidthInUse,
      alertBandwidthThreshold,
      alertAuditLogSizeUsed,
      alertAuditLogSizeThreshold,
      alertDiskSpaceUsageDiskName,
      alertDiskSpaceUsageCurrent,
      alertDiskSpaceUsageThreshold,
      alertCertificateExpirationCertificateName,
      alertCertificateExpirationDaysRemaining,
      alertCertificateExpiredCertificateName,
      alertCpuUsageCurrent,
      alertCpuUsageThreshold,
      alertCpuUsageThresholdWindow,
      alertMemoryUsageCurrent,
      alertMemoryUsageThreshold,  
      alertDmaName
   }
   STATUS current
   DESCRIPTION "A collection of alert-related objects."
   ::= { cmaNotificationConformance 1 }

alertSequenceNumber OBJECT-TYPE
   SYNTAX       Counter32
   MAX-ACCESS   accessible-for-notify
   STATUS       current
   DESCRIPTION  "Sequential ID number of the alert. Each alert ID 
                 on a specific CMA server is unique."
::= { cmaAlertObjectsGeneral 1 }

alertSeverity OBJECT-TYPE
   SYNTAX       ItuPerceivedSeverity
   MAX-ACCESS   accessible-for-notify
   STATUS       current
   DESCRIPTION  "Severity of the alert."
::= { cmaAlertObjectsGeneral 2 }

alertTimeStamp OBJECT-TYPE
   SYNTAX       DateAndTime
   MAX-ACCESS   accessible-for-notify
   STATUS       current
   DESCRIPTION  "Timestamp of the alert."
::= { cmaAlertObjectsGeneral 3 }

alertFailedServerInetAddressType OBJECT-TYPE
   SYNTAX       InetAddressType
   MAX-ACCESS   accessible-for-notify
   STATUS       current
   DESCRIPTION  "IP address type of the failed CMA server."
::= { cmaAlertObjectsGeneral 4 }

alertFailedServerInetAddress OBJECT-TYPE
   SYNTAX       InetAddress
   MAX-ACCESS   accessible-for-notify
   STATUS       current
   DESCRIPTION  "IP address of the failed CMA server."
::= { cmaAlertObjectsGeneral 5 }

alertActiveServerInetAddressType OBJECT-TYPE
   SYNTAX       InetAddressType
   MAX-ACCESS   accessible-for-notify
   STATUS       current
   DESCRIPTION  "IP address type of the active CMA server."
::= { cmaAlertObjectsGeneral 6 }

alertActiveServerInetAddress OBJECT-TYPE
   SYNTAX       InetAddress
   MAX-ACCESS   accessible-for-notify
   STATUS       current
   DESCRIPTION  "IP address of the active CMA server."
::= { cmaAlertObjectsGeneral 7 }

alertRedundantServerInetAddressType OBJECT-TYPE
   SYNTAX       InetAddressType
   MAX-ACCESS   accessible-for-notify
   STATUS       current
   DESCRIPTION  "IP address type of the redundant CMA server."
::= { cmaAlertObjectsGeneral 8 }

alertRedundantServerInetAddress OBJECT-TYPE
   SYNTAX       InetAddress
   MAX-ACCESS   accessible-for-notify
   STATUS       current
   DESCRIPTION  "IP address of the redundant CMA server."
::= { cmaAlertObjectsGeneral 9 }

alertCmaServerInetAddressType OBJECT-TYPE
   SYNTAX       InetAddressType
   MAX-ACCESS   accessible-for-notify
   STATUS       current
   DESCRIPTION  "IP address type of the CMA server."
::= { cmaAlertObjectsGeneral 10 }

alertCmaServerInetAddress OBJECT-TYPE
   SYNTAX       InetAddress
   MAX-ACCESS   accessible-for-notify
   STATUS       current
   DESCRIPTION  "IP address of the CMA server."
::= { cmaAlertObjectsGeneral 11 }

alertMcuName OBJECT-TYPE
   SYNTAX       OCTET STRING(SIZE (0..255))
   MAX-ACCESS   accessible-for-notify
   STATUS       current
   DESCRIPTION  "Name assigned to an MCU within the CMA"
   ::= { cmaAlertObjectsGeneral 12 }

alertCmaDbName OBJECT-TYPE
   SYNTAX       OCTET STRING(SIZE (0..255))
   MAX-ACCESS   accessible-for-notify
   STATUS       current
   DESCRIPTION  "CMA Database name."
::= { cmaAlertObjectsGeneral 15 } 

alertSiteName OBJECT-TYPE
   SYNTAX       OCTET STRING(SIZE (0..255))
   MAX-ACCESS   accessible-for-notify
   STATUS       current
   DESCRIPTION  "Name of the site."
   ::= { cmaAlertObjectsGeneral 18 }

alertSubnetInetAddressType OBJECT-TYPE
   SYNTAX       InetAddressType
   MAX-ACCESS   accessible-for-notify
   STATUS       current
   DESCRIPTION  "IP address type of the subnet."
::= { cmaAlertObjectsGeneral 19 }

alertSubnetInetAddress OBJECT-TYPE
   SYNTAX       InetAddress
   MAX-ACCESS   accessible-for-notify
   STATUS       current
   DESCRIPTION  "IP address of the subnet."
::= { cmaAlertObjectsGeneral 20 }

alertSubnetMask OBJECT-TYPE
   SYNTAX       InetAddress
   MAX-ACCESS   accessible-for-notify
   STATUS       current
   DESCRIPTION  "Subnet mask for the subnet."
::= { cmaAlertObjectsGeneral 21 }

alertSiteLinkName OBJECT-TYPE
   SYNTAX       OCTET STRING(SIZE (0..255))
   MAX-ACCESS   accessible-for-notify
   STATUS       current
   DESCRIPTION  "Name of the site link."
   ::= { cmaAlertObjectsGeneral 22 }

alertBandwidthInUse OBJECT-TYPE
   SYNTAX       Counter64
   MAX-ACCESS   accessible-for-notify
   STATUS       current
   DESCRIPTION  "Bandwidth in use for site, site link, or subnet being reported."
::= { cmaAlertObjectsGeneral 23 }

alertBandwidthThreshold OBJECT-TYPE
   SYNTAX       OCTET STRING(SIZE (0..255))
   MAX-ACCESS   accessible-for-notify
   STATUS       current
   DESCRIPTION  "Threshold that has been exceeded."
   ::= { cmaAlertObjectsGeneral 24 }

alertAuditLogSizeUsed OBJECT-TYPE
   SYNTAX       OCTET STRING(SIZE (0..255))
   MAX-ACCESS   accessible-for-notify
   STATUS       current
   DESCRIPTION  "Disc space used by audit log(s)."
   ::= { cmaAlertObjectsGeneral 25 }

alertAuditLogSizeThreshold OBJECT-TYPE
   SYNTAX       OCTET STRING(SIZE (0..255))
   MAX-ACCESS   accessible-for-notify
   STATUS       current
   DESCRIPTION  "Audit log size threshold that has been exceeded."
   ::= { cmaAlertObjectsGeneral 26 }

alertDiskSpaceUsageDiskName  OBJECT-TYPE
   SYNTAX       OCTET STRING(SIZE (0..255))
   MAX-ACCESS   accessible-for-notify
   STATUS       current
   DESCRIPTION  "Name of the hard disk partition exceeding the threshold."
   ::= { cmaAlertObjectsGeneral 27 }

alertDiskSpaceUsageCurrent  OBJECT-TYPE
   SYNTAX       OCTET STRING(SIZE (0..255))
   MAX-ACCESS   accessible-for-notify
   STATUS       current
   DESCRIPTION  "Current percentage of used space on the disk partition."
   ::= { cmaAlertObjectsGeneral 28 }
   
alertDiskSpaceUsageThreshold  OBJECT-TYPE
   SYNTAX       OCTET STRING(SIZE (0..255))
   MAX-ACCESS   accessible-for-notify
   STATUS       current
   DESCRIPTION  "Disk space usage threshold (percentage of used space)."
   ::= { cmaAlertObjectsGeneral 29 }
   
alertCertificateExpirationCertificateName  OBJECT-TYPE
   SYNTAX       OCTET STRING(SIZE (0..255))
   MAX-ACCESS   accessible-for-notify
   STATUS       current
   DESCRIPTION  "Name of the certificate the expiration warning is for."
   ::= { cmaAlertObjectsGeneral 30 }

alertCertificateExpirationDaysRemaining  OBJECT-TYPE
   SYNTAX       OCTET STRING(SIZE (0..255))
   MAX-ACCESS   accessible-for-notify
   STATUS       current
   DESCRIPTION  "Number of days remaining until the certificate will expire."
   ::= { cmaAlertObjectsGeneral 31 }
   
alertCertificateExpiredCertificateName  OBJECT-TYPE
   SYNTAX       OCTET STRING(SIZE (0..255))
   MAX-ACCESS   accessible-for-notify
   STATUS       current
   DESCRIPTION  "Name of the expired certificate."
   ::= { cmaAlertObjectsGeneral 32 }

alertCpuUsageCurrent  OBJECT-TYPE
   SYNTAX       OCTET STRING(SIZE (0..255))
   MAX-ACCESS   accessible-for-notify
   STATUS       current
   DESCRIPTION  "Current average CPU usage (percentage of used CPU)."
   ::= { cmaAlertObjectsGeneral 33 }

alertCpuUsageThreshold  OBJECT-TYPE
   SYNTAX       OCTET STRING(SIZE (0..255))
   MAX-ACCESS   accessible-for-notify
   STATUS       current
   DESCRIPTION  "Average CPU warning threshold (percentage of used CPU)."
   ::= { cmaAlertObjectsGeneral 34 }
   
alertCpuUsageThresholdWindow  OBJECT-TYPE
   SYNTAX       OCTET STRING(SIZE (0..255))
   MAX-ACCESS   accessible-for-notify
   STATUS       current
   DESCRIPTION  "Timeframe in minutes over which the CPU usage is averaged."
   ::= { cmaAlertObjectsGeneral 35 }
   
alertMemoryUsageCurrent  OBJECT-TYPE
   SYNTAX       OCTET STRING(SIZE (0..255))
   MAX-ACCESS   accessible-for-notify
   STATUS       current
   DESCRIPTION  "Current system memory usage (percentage of used memory)."
   ::= { cmaAlertObjectsGeneral 36 }
   
alertMemoryUsageThreshold  OBJECT-TYPE
   SYNTAX       OCTET STRING(SIZE (0..255))
   MAX-ACCESS   accessible-for-notify
   STATUS       current
   DESCRIPTION  "Memory Usage warning threshold (percentage of used memory)."
   ::= { cmaAlertObjectsGeneral 37 }

alertDmaName OBJECT-TYPE
   SYNTAX       OCTET STRING(SIZE (0..255))
   MAX-ACCESS   accessible-for-notify
   STATUS       current
   DESCRIPTION  "Name assigned to a DMA within the CMA"
   ::= { cmaAlertObjectsGeneral 38 }


-------------------------------------------------------------------------------
-- Alerts
-------------------------------------------------------------------------------
cmaAlertNotificationGroup  NOTIFICATION-GROUP
   NOTIFICATIONS
   {
      mcuDownAlert,
      dbConnectionDownAlert,
      ldapConnectionDownAlert,
      cmaFailoverAlert,
      licenseCapacityAlert,
      cmaMonitorServiceStoppedAlert,
      redundantServerDownAlert,
      redundantServerConflictAlert,
      ldapSystemAccountPasswordFailed,
      bandwidthUsedSiteAlert,
      bandwidthUsedSubnetAlert,
      bandwidthUsedSiteLinkAlert,
      auditUsageThresholdExceeded,
      alertDiskSpaceUsageExceeded,
      certificateExpirationWarning,
      certificateExpiredWarning,
      idsFloodDetected,
      databaseBackupFailed,
      cpuUsageExceededAlert,
      memoryUsageExceededAlert,
      licenseExpirationAlert,
      dmaDownAlert,
      provisioningCapacityAlert,
      autoSystemBackupFtpFailedAlert
   }
   STATUS  current
   DESCRIPTION "Notifications that the CMA SNMP agent is required to implement."
   ::= { cmaNotificationConformance 2 }

mcuDownAlert NOTIFICATION-TYPE
   OBJECTS { alertSequenceNumber, alertSeverity, alertTimeStamp, alertMcuName }
   STATUS       current
   DESCRIPTION  
        "Alert generated when the CMA server detects a loss of communication with an MCU."
   ::= { cmaAlertObjectsAlerts 1 }

dbConnectionDownAlert NOTIFICATION-TYPE
   OBJECTS { alertSequenceNumber, alertSeverity, alertTimeStamp, alertCmaDbName }
   STATUS       current
   DESCRIPTION  
        "Alert generated when the CMA server detects a connection loss with the CMA database."
   ::= { cmaAlertObjectsAlerts 2 }

ldapConnectionDownAlert NOTIFICATION-TYPE
   OBJECTS { alertSequenceNumber, alertSeverity, alertTimeStamp }
   STATUS       current
   DESCRIPTION  
        "Alert generated when the CMA server detects a connection loss with the LDAP server."
   ::= { cmaAlertObjectsAlerts 3 }

cmaFailoverAlert NOTIFICATION-TYPE
   OBJECTS { alertSequenceNumber, alertSeverity, alertTimeStamp, 
             alertFailedServerInetAddressType, alertFailedServerInetAddress, 
             alertActiveServerInetAddressType, alertActiveServerInetAddress }
   STATUS       current
   DESCRIPTION  
        "Alert generated when the CMA server fails over to the redundant server."
   ::= { cmaAlertObjectsAlerts 4 }

licenseCapacityAlert NOTIFICATION-TYPE
   OBJECTS { alertSequenceNumber, alertSeverity, alertTimeStamp }
   STATUS       current
   DESCRIPTION  
        "Alert generated when the percentage of used licenses reaches 5% of the maximum."
   ::= { cmaAlertObjectsAlerts 5 }

cmaMonitorServiceStoppedAlert NOTIFICATION-TYPE
   OBJECTS { alertSequenceNumber, alertSeverity, alertTimeStamp, alertCmaServerInetAddressType,
             alertCmaServerInetAddress }
   STATUS       current
   DESCRIPTION  
        "Alert generated when the CMA redundancy monitoring service stops on a CMA server.
         Contains the IP address of the server on which the monitoring service has stopped."
   ::= { cmaAlertObjectsAlerts 7 }

redundantServerDownAlert NOTIFICATION-TYPE
   OBJECTS { alertSequenceNumber, alertSeverity, alertTimeStamp, alertFailedServerInetAddressType,
             alertFailedServerInetAddress }
   STATUS       current
   DESCRIPTION  
        "Alert generated when the CMA server detects a connection loss with the 
         redundant CMA server."
   ::= { cmaAlertObjectsAlerts 8 }

redundantServerConflictAlert NOTIFICATION-TYPE
   OBJECTS { alertSequenceNumber, alertSeverity, alertTimeStamp, 
             alertActiveServerInetAddressType, alertActiveServerInetAddress, 
             alertRedundantServerInetAddressType, alertRedundantServerInetAddress }
   STATUS       current
   DESCRIPTION  
        "Alert generated if the active and redundant CMA servers are both 
         running in active mode."
   ::= { cmaAlertObjectsAlerts 9 }

ldapSystemAccountPasswordFailed NOTIFICATION-TYPE
   OBJECTS { alertSequenceNumber, alertSeverity, alertTimeStamp }
   STATUS       current
   DESCRIPTION  
        "Alert generated if the CMA server cannot connect to the LDAP server using 
         the configured LDAP system account."
   ::= { cmaAlertObjectsAlerts 10 }

bandwidthUsedSiteAlert NOTIFICATION-TYPE
   OBJECTS { alertSequenceNumber, alertSeverity, alertTimeStamp, alertSiteName,
             alertBandwidthInUse, alertBandwidthThreshold }
   STATUS       current
   DESCRIPTION  
        "Alert generated when the CMA server detects bandwidth usage for a site 
         has exceeded an upper threshold."
   ::= { cmaAlertObjectsAlerts 14 }

bandwidthUsedSubnetAlert NOTIFICATION-TYPE
   OBJECTS { alertSequenceNumber, alertSeverity, alertTimeStamp, alertSiteName,
             alertSubnetInetAddressType, alertSubnetInetAddress, alertSubnetMask,
             alertBandwidthInUse, alertBandwidthThreshold }
   STATUS       current
   DESCRIPTION  
        "Alert generated when the CMA server detects bandwidth usage for a site has exceeded an upper threshold."
   ::= { cmaAlertObjectsAlerts 15 }

bandwidthUsedSiteLinkAlert NOTIFICATION-TYPE
   OBJECTS { alertSequenceNumber, alertSeverity, alertTimeStamp, alertSiteLinkName,
             alertBandwidthInUse, alertBandwidthThreshold }
   STATUS       current
   DESCRIPTION  
        "Alert generated when the CMA server detects bandwidth usage for a site has exceeded an upper threshold."
   ::= { cmaAlertObjectsAlerts 16 }

auditUsageThresholdExceeded NOTIFICATION-TYPE
   OBJECTS { alertSequenceNumber, alertSeverity, alertTimeStamp, alertAuditLogSizeUsed, alertAuditLogSizeThreshold }
   STATUS       current
   DESCRIPTION  
        "Alert generated when the disc usage for audit logs exceeds the defined threshold."
   ::= { cmaAlertObjectsAlerts 17 }

alertDiskSpaceUsageExceeded NOTIFICATION-TYPE
   OBJECTS { alertSequenceNumber, alertSeverity, alertTimeStamp, alertDiskSpaceUsageDiskName, alertDiskSpaceUsageCurrent, alertDiskSpaceUsageThreshold }
   STATUS       current
   DESCRIPTION  
        "Alert generated when the disc usage for the system exceeds the defined threshold."
   ::= { cmaAlertObjectsAlerts 18 }

certificateExpirationWarning NOTIFICATION-TYPE
   OBJECTS { alertSequenceNumber, alertSeverity, alertTimeStamp, alertCertificateExpirationCertificateName, alertCertificateExpirationDaysRemaining }
   STATUS       current
   DESCRIPTION  
        "Alert generated when the CMA certificate is nearing expiration."
   ::= { cmaAlertObjectsAlerts 19 }

certificateExpiredWarning NOTIFICATION-TYPE
   OBJECTS { alertSequenceNumber, alertSeverity, alertTimeStamp, alertCertificateExpiredCertificateName }
   STATUS       current
   DESCRIPTION  
        "Alert generated when the CMA certificate has expired."
   ::= { cmaAlertObjectsAlerts 20 }

idsFloodDetected NOTIFICATION-TYPE
   OBJECTS { alertSequenceNumber, alertSeverity, alertTimeStamp }
   STATUS       current
   DESCRIPTION  
        "The frequency of network intrusion events has exceeded the defined threshold."
   ::= { cmaAlertObjectsAlerts 23 }

databaseBackupFailed NOTIFICATION-TYPE
   OBJECTS { alertSequenceNumber, alertSeverity, alertTimeStamp }
   STATUS       current
   DESCRIPTION  
        "Backup of the database has failed."
   ::= { cmaAlertObjectsAlerts 26 }

cpuUsageExceededAlert NOTIFICATION-TYPE
   OBJECTS { alertSequenceNumber, alertSeverity, alertTimeStamp, alertCpuUsageCurrent, alertCpuUsageThreshold, alertCpuUsageThresholdWindow }
   STATUS       current
   DESCRIPTION  
        "Alert generated when the average CPU Usage has exceeding the defined threshold."
   ::= { cmaAlertObjectsAlerts 30 }

memoryUsageExceededAlert NOTIFICATION-TYPE
   OBJECTS { alertSequenceNumber, alertSeverity, alertTimeStamp, alertMemoryUsageCurrent, alertMemoryUsageThreshold }
   STATUS       current
   DESCRIPTION  
        "Alert generated when the memory usage reached or exceeds the defined threshold."
   ::= { cmaAlertObjectsAlerts 31 }
   
licenseExpirationAlert NOTIFICATION-TYPE
   OBJECTS { alertSequenceNumber, alertSeverity, alertTimeStamp }
   STATUS       current
   DESCRIPTION  
        "Alert generated when the license has already or will expire within 30 days."
   ::= { cmaAlertObjectsAlerts 32 }

dmaDownAlert NOTIFICATION-TYPE
   OBJECTS { alertSequenceNumber, alertSeverity, alertTimeStamp, alertDmaName }
   STATUS       current
   DESCRIPTION  
        "Alert generated when the CMA server detects a loss of communication with a DMA."
   ::= { cmaAlertObjectsAlerts 34 }
      
provisioningCapacityAlert NOTIFICATION-TYPE
   OBJECTS { alertSequenceNumber, alertSeverity, alertTimeStamp, alertDmaName }
   STATUS       current
   DESCRIPTION  
        "System Capability Settings for Managed Endpoint and Services Number Exceeded."
   ::= { cmaAlertObjectsAlerts 35 }

autoSystemBackupFtpFailedAlert NOTIFICATION-TYPE
   OBJECTS { alertSequenceNumber, alertSeverity, alertTimeStamp, alertDmaName }
   STATUS       current
   DESCRIPTION  
        "Auto System Backup Failure."
   ::= { cmaAlertObjectsAlerts 36 }
      
END
