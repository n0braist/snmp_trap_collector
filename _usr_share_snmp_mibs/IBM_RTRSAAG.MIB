-- ***************************************************************************
-- ***************************************************************************
--
-- File         : rtrsaag.mib
-- Description  : IBM Remote Supervisor Adapter II MIB for SNMP
-- By           : Joe Bolan, IBM
-- Update by    : Phuong Nguyen, IBM
-- Version      : 1.0
-- Date         : April 2, 2003
--
--
-- Copyright (c) 2001 IBM  All Rights Reserved.
--
--
-- Contains MIB description for:
--   This MIB is to be used to provide configuration support of both
--   Remote Supervisor Adapter I and II as well as monitoring support
--   for the system.
-- ***************************************************************************
-- Note:
--
-- The following OIDs DO NOT include the ASM command number. (Note,
-- the end portion of most OIDs will contain the ASM dot command number.)
--  (1) currentSysPwrStatus
--  (2) powerOnHours
--  (3) restartCount
--  (4) systemState
--  (5) generateTestAlert
--  (6) VPD
--  (7) Thresholds
--  (8) PCI-X expansion enclosure
--  (9) Timezone (GMT and DST)

-- ***************************************************************************
-- ***************************************************************************
-- Revisions:
--  04/02/2003  PN   Modified and revised from Falcon for Raptor
--  12/12/2003  BN   Removed PPP option for port1Function
--  01/07/2004  BN   Added Telnet Connection Count and Disallow command on
--                   USB interface
--  01/20/2004  BN   Swapped remoteAlertEntryDelay with remoteAlertRetryDelay
--  02/02/2004  BN   Changed some wordings in powerSysConfig
--  03/09/2004  BN   Added firmware update
--  03/31/2004  BN   Changed spHostOsPlatform to display either "other" or
--                   "linux"
--  04/06/2004  BN   Changed RootFilter to GroupFiler for LDAP
--  04/15/2004  BN   Added DNS option for LDAP
--  06/07/2004  BN   Fixed compilation problem on IBM Director
--  06/21/2004  BN   Changed commandModeEnable to commandMode
--  06/23/2004  PTN  Add 4.9.3.4.5 & 4.9.3.4.6
--  07/07/2004  BN   Correct range on OCTET STRING for IBM Director
--  07/26/2004  BN   Remove Serial port for x236_pereg and x346_pereg
--  09/20/2004  BN   Remove underscore in MIB SYNTAX
--  09/16/2005  EK   Typo in 4.9.3.4.4 "diabled" should be "disabled"
--  12/27/2005  MM   Added Fans 9 - 12
--  10/25/2006  MG   Add snmpCommunityEntryCommunityViewType
--  11/14/2006  EK   Added 4.2.3.16
-- ***************************************************************************
        RSA-MIB DEFINITIONS ::= BEGIN


        IMPORTS
            OBJECT-TYPE                          FROM RFC-1212
            enterprises                          FROM RFC1155-SMI
            -- DisplayString                        FROM RFC1213-MIB
            IpAddress                            FROM RFC1155-SMI
            TRAP-TYPE                            FROM RFC-1215;

        -- IBM enterprise group
        ibm         OBJECT IDENTIFIER ::=   { enterprises 2 }

        -- IBM products group
        ibmAgents      OBJECT IDENTIFIER ::=   { ibm 3 }

        -- IBM e-Server Advanced System Management Support Processor(SP) agent group
        netfinitySupportProcessorAgent OBJECT IDENTIFIER ::= { ibmAgents 51 }

        -- IBM Remote Supervisor Adapter (increase this number for follow on SP's)
        --   Also known as Advanced System Mangement(ASM) SP
        ibmRemoteSupSnmpMIB     OBJECT IDENTIFIER ::= { netfinitySupportProcessorAgent 1 }

-- ***************************************************************************
-- Start: Define groups of objects within the ibmRemoteSupSnmpMIB
-- ***************************************************************************
  --This group of objects provides the various environmental monitors for the
  -- local system and the ASM
  monitors OBJECT IDENTIFIER ::= { ibmRemoteSupSnmpMIB 2 }

  --This group of objects provides the error log objects for the ASM
  errorLogs OBJECT IDENTIFIER ::= { ibmRemoteSupSnmpMIB 3 }

  --This group of objects provides configuration functions for the ASM
  configureSP     OBJECT IDENTIFIER ::= { ibmRemoteSupSnmpMIB 4 }

  --This group of objects provides configuration functions for the system(server)
  generalSystemSettings  OBJECT IDENTIFIER ::= { ibmRemoteSupSnmpMIB 5 }

  --This group of objects provides configuration functions for system power
  systemPower  OBJECT IDENTIFIER ::= { ibmRemoteSupSnmpMIB 6 }

  --This group of objects provides functions to boot the ASM and system
  restartReset      OBJECT IDENTIFIER ::= { ibmRemoteSupSnmpMIB 7 }

  --This group of objects provides functions to update the ASM firmware
  firmwareUpdate    OBJECT IDENTIFIER ::= { ibmRemoteSupSnmpMIB 8 }

  --This group of objects provides information on the PCI-X expansion enclosure
  pcixExpansionBox      OBJECT IDENTIFIER ::= { ibmRemoteSupSnmpMIB 21 }

-- ****************************************************************************
--  Monitors
-- ****************************************************************************
    -- ************************************************************************
    -- Temperature
    -- ************************************************************************
    temperature OBJECT IDENTIFIER ::= { monitors 1 }
     --Planar Temperature
     planarTemp OBJECT IDENTIFIER ::= { temperature 1 }

      ccTemp       OBJECT-TYPE
                   SYNTAX  OCTET STRING
                   ACCESS  read-only
                   STATUS  mandatory
                   DESCRIPTION
                   "System's planar temperature in degrees centigrade(C).
                   An octet string expressed as 'sddd.dd Centigrade' where:
                   s is the sign ('-' for negative or blank space for positive)
                   d is a decimal digit or blank space for a leading zero.
                   The string 'Not Readable!' indicates that the given monitor
                   is not supported on this system."
                   ::= { planarTemp 1 }

        asmTemp      OBJECT-TYPE
                     SYNTAX  OCTET STRING
                     ACCESS  read-only
                     STATUS  mandatory
                     DESCRIPTION
                     "ASM Card temperature in degrees centigrade(C).
                     An octet string expressed as 'sddd.dd Centigrade' where:
                     s is the sign ('-' for negative or blank space for positive)
                     d is a decimal digit or blank space for leading zeroes.
                     The string 'Not Readable!' indicates that the given monitor
                    is not supported on this system."
                     ::= { planarTemp 2 }

      cpuAreaTemp  OBJECT-TYPE
                   SYNTAX  OCTET STRING
                   ACCESS  read-only
                   STATUS  mandatory
                   DESCRIPTION
                   "System CPU area of the planar temperature in degrees centigrade(C).
                   An octet string expressed as 'sddd.dd Centigrade' where:
                   s is the sign ('-' for negative or blank space for positive)
                   d is a decimal digit or blank space for leading zeroes.
                   The string 'Not Readable!' indicates that the given monitor
                   is not supported on this system."
                   ::= { planarTemp 3}


      ioAreaTemp   OBJECT-TYPE
                   SYNTAX  OCTET STRING
                   ACCESS  read-only
                   STATUS  mandatory
                   DESCRIPTION
                   "System I/O area of the planar temperature in degrees centigrade(C).
                   An octet string expressed as 'sddd.dd Centigrade' where:
                   s is the sign ('-' for negative or blank space for positive)
                   d is a decimal digit or blank space for leading zeroes.
                   The string 'Not Readable!' indicates that the given monitor
                   is not supported on this system."
                   ::= { planarTemp 5}


      memAreaTemp  OBJECT-TYPE
                   SYNTAX  OCTET STRING
                   ACCESS  read-only
                   STATUS  mandatory
                   DESCRIPTION
                   "System memory area of the planar temperature in degrees centigrade(C).
                   An octet string expressed as 'sddd.dd Centigrade' where:
                   s is the sign ('-' for negative or blank space for positive)
                   d is a decimal digit or blank space for leading zeroes.
                   The string 'Not Readable!' indicates that the given monitor
                   is not supported on this system."
                   ::= { planarTemp 6}


     --CPUx Temperature
     cpuXTemp OBJECT IDENTIFIER ::= { temperature 2 }

      cpu1Temp     OBJECT-TYPE
                   SYNTAX  OCTET STRING
                   ACCESS  read-only
                   STATUS  mandatory
                   DESCRIPTION
                   "CPU 1 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 1 }

      cpu2Temp     OBJECT-TYPE
                   SYNTAX  OCTET STRING
                   ACCESS  read-only
                   STATUS  mandatory
                   DESCRIPTION
                   "CPU 2 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 2 }

      cpu3Temp     OBJECT-TYPE
                   SYNTAX  OCTET STRING
                   ACCESS  read-only
                   STATUS  mandatory
                   DESCRIPTION
                   "CPU 3 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 3 }

      cpu4Temp     OBJECT-TYPE
                   SYNTAX  OCTET STRING
                   ACCESS  read-only
                   STATUS  mandatory
                   DESCRIPTION
                   "CPU 4 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 4 }

      cpu5Temp     OBJECT-TYPE
                   SYNTAX  OCTET STRING
                   ACCESS  read-only
                   STATUS  mandatory
                   DESCRIPTION
                   "CPU 5 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 5 }

      cpu6Temp     OBJECT-TYPE
                   SYNTAX  OCTET STRING
                   ACCESS  read-only
                   STATUS  mandatory
                   DESCRIPTION
                   "CPU 6 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 6 }

      cpu7Temp     OBJECT-TYPE
                   SYNTAX  OCTET STRING
                   ACCESS  read-only
                   STATUS  mandatory
                   DESCRIPTION
                   "CPU 7 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 7 }

      cpu8Temp     OBJECT-TYPE
                   SYNTAX  OCTET STRING
                   ACCESS  read-only
                   STATUS  mandatory
                   DESCRIPTION
                   "CPU 8 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { cpuXTemp 8 }

     --DASDx Temperature
     dasdXTemp OBJECT IDENTIFIER ::= { temperature 4 }

      dasd1Temp    OBJECT-TYPE
                   SYNTAX  OCTET STRING
                   ACCESS  read-only
                   STATUS  mandatory
                   DESCRIPTION
                   "DASD 1 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { dasdXTemp 1 }

      dasd2Temp    OBJECT-TYPE
                   SYNTAX  OCTET STRING
                   ACCESS  read-only
                   STATUS  mandatory
                   DESCRIPTION
                   "DASD 2 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { dasdXTemp 2 }

      dasd3Temp    OBJECT-TYPE
                   SYNTAX  OCTET STRING
                   ACCESS  read-only
                   STATUS  mandatory
                   DESCRIPTION
                   "DASD 3 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { dasdXTemp 3 }

      dasd4Temp    OBJECT-TYPE
                   SYNTAX  OCTET STRING
                   ACCESS  read-only
                   STATUS  mandatory
                   DESCRIPTION
                   "DASD 4 temperature in degrees centigrade(C).
                   An octet string expressed as 'sddd.dd Centigrade' where:
                   s is the sign ('-' for negative or blank space for positive)
                   d is a decimal digit or blank space for a leading zero..
                   The string 'Not Readable!' indicates that the given monitor
                   is not supported on this system."
                   ::= { dasdXTemp 4 }

     --System Ambient Temperature
     ambientTemp OBJECT IDENTIFIER ::= { temperature 5 }

      systemAmbientTemp    OBJECT-TYPE
                   SYNTAX  OCTET STRING
                   ACCESS  read-only
                   STATUS  mandatory
                   DESCRIPTION
                   "System's ambient temperature in degrees centigrade(C).
                   This is surrounding temperature where the system is installed.
                   An octet string expressed as 'sddd.dd Centigrade' where:
                   s is the sign ('-' for negative or blank space for positive)
                   d is a decimal digit or blank space for a leading zero..
                   The string 'Not Readable!' indicates that the given monitor
                   is not supported on this system."
                   ::= { ambientTemp 1 }

    -- ************************************************************************
    -- Voltages
    -- ************************************************************************
    voltage OBJECT IDENTIFIER ::= { monitors 2 }
     --Planar Voltages
     planarVolt OBJECT IDENTIFIER ::= { voltage 1 }

      plus5Volt     OBJECT-TYPE
                   SYNTAX  OCTET STRING
                   ACCESS  read-only
                   STATUS  mandatory
                   DESCRIPTION
                   "+5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 1 }

      plus3Pt3Volt OBJECT-TYPE
                   SYNTAX  OCTET STRING
                   ACCESS  read-only
                   STATUS  mandatory
                   DESCRIPTION
                   "+3 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 2 }

      plus12Volt    OBJECT-TYPE
                   SYNTAX  OCTET STRING
                   ACCESS  read-only
                   STATUS  mandatory
                   DESCRIPTION
                   "+12 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 3 }

      minus12Volt    OBJECT-TYPE
                   SYNTAX  OCTET STRING
                   ACCESS  read-only
                   STATUS  mandatory
                   DESCRIPTION
                   "-12 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 4 }

      minus5Volt     OBJECT-TYPE
                   SYNTAX  OCTET STRING
                   ACCESS  read-only
                   STATUS  mandatory
                   DESCRIPTION
                   "-5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 5 }

      plus2Pt5Volt  OBJECT-TYPE
                   SYNTAX  OCTET STRING
                   ACCESS  read-only
                   STATUS  mandatory
                   DESCRIPTION
                   "+2.5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 6 }

      plus1Pt5Volt  OBJECT-TYPE
                   SYNTAX  OCTET STRING
                   ACCESS  read-only
                   STATUS  mandatory
                   DESCRIPTION
                   "+1.5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 7 }

      plus1Pt25Volt OBJECT-TYPE
                   SYNTAX  OCTET STRING
                   ACCESS  read-only
                   STATUS  mandatory
                   DESCRIPTION
                   "+1.25 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 13 }

     --Voltage Regulator Module Voltages
     vrmVolt OBJECT IDENTIFIER ::= { voltage 3 }

      vrm1Volt     OBJECT-TYPE
                   SYNTAX  OCTET STRING
                   ACCESS  read-only
                   STATUS  mandatory
                   DESCRIPTION
                   "VRM 1 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 1 }

      vrm2Volt     OBJECT-TYPE
                   SYNTAX  OCTET STRING
                   ACCESS  read-only
                   STATUS  mandatory
                   DESCRIPTION
                   "VRM 2 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 2 }

      vrm3Volt     OBJECT-TYPE
                   SYNTAX  OCTET STRING
                   ACCESS  read-only
                   STATUS  mandatory
                   DESCRIPTION
                   "VRM 3 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 3 }

      vrm4Volt     OBJECT-TYPE
                   SYNTAX  OCTET STRING
                   ACCESS  read-only
                   STATUS  mandatory
                   DESCRIPTION
                   "VRM 4 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 4 }

      vrm5Volt     OBJECT-TYPE
                   SYNTAX  OCTET STRING
                   ACCESS  read-only
                   STATUS  mandatory
                   DESCRIPTION
                   "VRM 5 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 5 }

      vrm6Volt     OBJECT-TYPE
                   SYNTAX  OCTET STRING
                   ACCESS  read-only
                   STATUS  mandatory
                   DESCRIPTION
                   "VRM 6 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 6 }

      vrm7Volt     OBJECT-TYPE
                   SYNTAX  OCTET STRING
                   ACCESS  read-only
                   STATUS  mandatory
                   DESCRIPTION
                   "VRM 7 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 7 }

      vrm8Volt     OBJECT-TYPE
                   SYNTAX  OCTET STRING
                   ACCESS  read-only
                   STATUS  mandatory
                   DESCRIPTION
                   "VRM 8 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 8 }

      vrm9Volt     OBJECT-TYPE
                   SYNTAX  OCTET STRING
                   ACCESS  read-only
                   STATUS  mandatory
                   DESCRIPTION
                   "VRM 9 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 9 }

      vrm10Volt    OBJECT-TYPE
                   SYNTAX  OCTET STRING
                   ACCESS  read-only
                   STATUS  mandatory
                   DESCRIPTION
                   "VRM 10 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 10 }

      vrm11Volt    OBJECT-TYPE
                   SYNTAX  OCTET STRING
                   ACCESS  read-only
                   STATUS  mandatory
                   DESCRIPTION
                   "VRM 11 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 11 }

      vrm12Volt    OBJECT-TYPE
                   SYNTAX  OCTET STRING
                   ACCESS  read-only
                   STATUS  mandatory
                   DESCRIPTION
                   "VRM 12 voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { vrmVolt 12 }
    -- ************************************************************************
    -- Fans
    -- ************************************************************************
    fans OBJECT IDENTIFIER ::= { monitors 3 }

     fan1speed    OBJECT-TYPE
                  SYNTAX  OCTET STRING
                  ACCESS  read-only
                  STATUS  mandatory
                  DESCRIPTION
                  "Fan 1 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 1 }

     fan2speed    OBJECT-TYPE
                  SYNTAX  OCTET STRING
                  ACCESS  read-only
                  STATUS  mandatory
                  DESCRIPTION
                  "Fan 2 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 2 }

     fan3speed    OBJECT-TYPE
                  SYNTAX  OCTET STRING
                  ACCESS  read-only
                  STATUS  mandatory
                  DESCRIPTION
                  "Fan 3 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."

                  ::= { fans 3 }

     fan4speed    OBJECT-TYPE
                  SYNTAX  OCTET STRING
                  ACCESS  read-only
                  STATUS  mandatory
                  DESCRIPTION
                  "Fan 4 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 4 }

     fan5speed    OBJECT-TYPE
                  SYNTAX  OCTET STRING
                  ACCESS  read-only
                  STATUS  mandatory
                  DESCRIPTION
                  "Fan 5 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 5 }

     fan6speed    OBJECT-TYPE
                  SYNTAX  OCTET STRING
                  ACCESS  read-only
                  STATUS  mandatory
                  DESCRIPTION
                  "Fan 6 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 6 }

     fan7speed    OBJECT-TYPE
                  SYNTAX  OCTET STRING
                  ACCESS  read-only
                  STATUS  mandatory
                  DESCRIPTION
                  "Fan 7 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 7 }

     fan8speed    OBJECT-TYPE
                  SYNTAX  OCTET STRING
                  ACCESS  read-only
                  STATUS  mandatory
                  DESCRIPTION
                  "Fan 8 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 8 }

     fan9speed    OBJECT-TYPE
                  SYNTAX  OCTET STRING
                  ACCESS  read-only
                  STATUS  mandatory
                  DESCRIPTION
                  "Fan 9 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 9 }

     fan10speed   OBJECT-TYPE
                  SYNTAX  OCTET STRING
                  ACCESS  read-only
                  STATUS  mandatory
                  DESCRIPTION
                  "Fan 10 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 10 }

     fan11speed   OBJECT-TYPE
                  SYNTAX  OCTET STRING
                  ACCESS  read-only
                  STATUS  mandatory
                  DESCRIPTION
                  "Fan 11 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 11 }

     fan12speed   OBJECT-TYPE
                  SYNTAX  OCTET STRING
                  ACCESS  read-only
                  STATUS  mandatory
                  DESCRIPTION
                  "Fan 12 speed expressed in percent(%) of maximum RPM.
                  An octet string expressed as 'ddd% of maximum' where:
                  d is a decimal digit or blank space for a leading zero.
                  If the fan is determined not to be running or
                  the fan speed cannot be determined, the string will
                  indicate 'Offline'.
                  The string 'Not Readable!' indicates that the given monitor
                  is not supported on this system."
                  ::= { fans 12 }


    -- ************************************************************************
    -- System Health
    -- ************************************************************************
    systemHealth OBJECT IDENTIFIER ::= { monitors 7 }

     -- ***********************************************************************
     -- System Health Status
     -- ***********************************************************************
     systemHealthStat  OBJECT-TYPE
                  SYNTAX  INTEGER {
                                    critical(0),
                                    nonCritical(2),
                                    systemLevel(4),
                                    normal(255)
                                  }
                  ACCESS  read-only
                  STATUS  mandatory
                  DESCRIPTION
                  "Indicates status of system health for the
                  system in which the ASM resides.
                  Value of 'critical' indicates a severe error has occurred
                  and the system may not be functioning. A value of
                  'nonCritical' indicates that a error has occurred but
                  the system is currently functioning properly.A value of
                  'systemLevel' indicates that a condition has occurred
                  that may change the state of the system in the future but currently
                  the system is working properly. A value of
                  'normal' indicates that the system is operating normally."
                  ::= { systemHealth 1 }

     -- ***********************************************************************
     -- System Health Summary
     -- ***********************************************************************
     systemHealthSummaryTable OBJECT-TYPE
                   SYNTAX  SEQUENCE OF SystemHealthSummaryEntry
                   ACCESS  not-accessible
                   STATUS  mandatory
                   DESCRIPTION
                   "Table of System Health summary. Contains more detailed
                   information about the reasons for the overall system
                   health status."
                   ::= { systemHealth 2 }

     systemHealthSummaryEntry OBJECT-TYPE
                   SYNTAX SystemHealthSummaryEntry
                   ACCESS  not-accessible
                   STATUS  mandatory
                   DESCRIPTION
                   "System Health Summary entry"
                   INDEX { systemHealthSummaryIndex }
                   ::= { systemHealthSummaryTable 1 }


     SystemHealthSummaryEntry ::= SEQUENCE {
                 systemHealthSummaryIndex INTEGER,
                 systemHealthSummarySeverity OCTET STRING,
                 systemHealthSummaryDescription OCTET STRING
     }


     systemHealthSummaryIndex  OBJECT-TYPE
                 SYNTAX  INTEGER
                 ACCESS  read-only
                 STATUS  mandatory
                 DESCRIPTION
                 "System health summary index."
                 ::= { systemHealthSummaryEntry 1 }

     systemHealthSummarySeverity  OBJECT-TYPE
                 SYNTAX  OCTET STRING
                 ACCESS  read-only
                 STATUS  mandatory
                 DESCRIPTION
                 "System health summary severity."
                 ::= { systemHealthSummaryEntry 2 }

     systemHealthSummaryDescription  OBJECT-TYPE
                 SYNTAX  OCTET STRING
                 ACCESS  read-only
                 STATUS  mandatory
                 DESCRIPTION
                 "System health summary description."
                 ::= { systemHealthSummaryEntry 3 }

     -- ***********************************************************************
     -- Environmental Monitor Thresholds
     -- ***********************************************************************
     monitorThresholds  OBJECT IDENTIFIER ::= { monitors 20 }

      -- **********************************************************************
      -- Temperature Thresholds
      -- **********************************************************************
      tempThresholds  OBJECT IDENTIFIER ::= { monitorThresholds 1 }


       generalSystemTempThresholds OBJECT IDENTIFIER ::= { tempThresholds 1 }


        generalTempThresholdsTable  OBJECT-TYPE
                              SYNTAX  SEQUENCE OF GeneralTempThresholdsEntry
                              ACCESS  not-accessible
                              STATUS  mandatory
                              DESCRIPTION
                              "Table of General Temperature threshold entries.
                              Has information about the Planar temperature and
                              System Ambient temperature."
                              ::= {  generalSystemTempThresholds 1 }

        generalTempThresholdsEntry  OBJECT-TYPE
                              SYNTAX  GeneralTempThresholdsEntry
                              ACCESS  not-accessible
                              STATUS  mandatory
                              DESCRIPTION
                              "General Temperature threshold entries."
                              INDEX { generalTempThresholdEntryIndex }
                              ::= { generalTempThresholdsTable 1 }

        GeneralTempThresholdsEntry ::= SEQUENCE {
                     generalTempThresholdEntryIndex INTEGER(0..255),
                     generalTempThresholdEntryName OCTET STRING (SIZE(0..16)),
                     generalTempThresholdEntryCurrentValue OCTET STRING,
                     generalTempThresholdEntryHardShutdownValue OCTET STRING,
                     generalTempThresholdEntrySoftShutdownValue OCTET STRING,
                     generalTempThresholdEntryWarningValue OCTET STRING,
                     generalTempThresholdEntryWarningResetValue OCTET STRING
        }


        generalTempThresholdEntryIndex  OBJECT-TYPE
                                  SYNTAX  INTEGER(0..255)
                                  ACCESS  read-only
                                  STATUS  mandatory
                                  DESCRIPTION
                                  "Index for a general temperature threshold entry."
                                  ::= { generalTempThresholdsEntry 1 }

        generalTempThresholdEntryName  OBJECT-TYPE
                                  SYNTAX  OCTET STRING (SIZE(0..16))
                                  ACCESS  read-only
                                  STATUS  mandatory
                                  DESCRIPTION
                                  "Null terminated string that
                                  contains the individual temperature monitor's name."
                                  ::= { generalTempThresholdsEntry 2 }

        generalTempThresholdEntryCurrentValue OBJECT-TYPE
                                    SYNTAX  OCTET STRING
                                    ACCESS  read-only
                                    STATUS  mandatory
                                    DESCRIPTION
                                    "Temperature in degrees centigrade(C).
                                    An octet string expressed as 'sddd.dd Centigrade' where:
                                    s is the sign ('-' for negative or blank space for positive)
                                    d is a decimal digit or blank space for a leading zero.
                                    The string 'Not Readable!' indicates that the given monitor
                                    is not supported on this system."
                                    ::= { generalTempThresholdsEntry 3 }

        generalTempThresholdEntryHardShutdownValue OBJECT-TYPE
                                    SYNTAX  OCTET STRING
                                    ACCESS  read-only
                                    STATUS  mandatory
                                    DESCRIPTION
                                    "Temperature in degrees centigrade(C).
                                    If the component's temperature rises above this value the
                                    system will be powered off immediately.
                                    If enabled, a critical alert/event will be generated.
                                    An octet string expressed as 'sddd.dd Centigrade' where:
                                    s is the sign ('-' for negative or blank space for positive)
                                    d is a decimal digit or blank space for a leading zero.
                                    The string 'Not Readable!' indicates that the given monitor
                                    is not supported on this system."
                                    ::= { generalTempThresholdsEntry 4 }

        generalTempThresholdEntrySoftShutdownValue OBJECT-TYPE
                                    SYNTAX  OCTET STRING
                                    ACCESS  read-only
                                    STATUS  mandatory
                                    DESCRIPTION
                                    "Temperature in degrees centigrade(C).
                                    If the component's temperature rises above this value the
                                    system will be powered off after the O/S is shut down.
                                    If enabled, a critical alert/event is generated.
                                    An octet string expressed as 'sddd.dd Centigrade' where:
                                    s is the sign ('-' for negative or blank space for positive)
                                    d is a decimal digit or blank space for a leading zero.
                                    The string 'Not Readable!' indicates that the given monitor
                                    is not supported on this system."
                                    ::= { generalTempThresholdsEntry 5 }

        generalTempThresholdEntryWarningValue OBJECT-TYPE
                                    SYNTAX  OCTET STRING
                                    ACCESS  read-only
                                    STATUS  mandatory
                                    DESCRIPTION
                                    "Temperature in degrees centigrade(C).
                                    If the temperature rises above this value a warning alert/event
                                    if enabled will be generated.
                                    An octet string expressed as 'sddd.dd Centigrade' where:
                                    s is the sign ('-' for negative or blank space for positive)
                                    d is a decimal digit or blank space for a leading zero.
                                    The string 'Not Readable!' indicates that the given monitor
                                    is not supported on this system."
                                    ::= { generalTempThresholdsEntry 6 }

        generalTempThresholdEntryWarningResetValue OBJECT-TYPE
                                    SYNTAX  OCTET STRING
                                    ACCESS  read-only
                                    STATUS  mandatory
                                    DESCRIPTION
                                    "Temperature in degrees centigrade(C).
                                    If the temperature rises above this value and
                                    if a warning alert/event had previously been
                                    created then the alert/event will be reset.
                                    An octet string expressed as 'sddd.dd Centigrade' where:
                                    s is the sign ('-' for negative or blank space for positive)
                                    d is a decimal digit or blank space for a leading zero.
                                    The string 'Not Readable!' indicates that the given monitor
                                    is not supported on this system."
                                    ::= { generalTempThresholdsEntry 7 }


       -- ***********************************************************************
       -- CPU X Temperature Thresholds
       -- ***********************************************************************

       cpuXTempThresholds OBJECT IDENTIFIER ::= { tempThresholds 5 }


        cpuTempThresholdsTable  OBJECT-TYPE
                              SYNTAX  SEQUENCE OF CpuTempThresholdsEntry
                              ACCESS  not-accessible
                              STATUS  mandatory
                              DESCRIPTION
                              "Table of CPU Temperature threshold entries."
                              ::= {  cpuXTempThresholds 1 }

        cpuTempThresholdsEntry  OBJECT-TYPE
                              SYNTAX  CpuTempThresholdsEntry
                              ACCESS  not-accessible
                              STATUS  mandatory
                              DESCRIPTION
                              "CPU Temperature threshold entries."
                              INDEX { cpuTempThresholdEntryIndex }
                              ::= { cpuTempThresholdsTable 1 }

        CpuTempThresholdsEntry ::= SEQUENCE {
                     cpuTempThresholdEntryIndex INTEGER(0..255),
                     cpuTempThresholdEntryName OCTET STRING (SIZE(0..16)),
                     cpuTempThresholdEntryCurrentValue OCTET STRING,
                     cpuTempThresholdEntryHardShutdownValue OCTET STRING,
                     cpuTempThresholdEntrySoftShutdownValue OCTET STRING,
                     cpuTempThresholdEntryWarningValue OCTET STRING,
                     cpuTempThresholdEntryWarningResetValue OCTET STRING
        }


        cpuTempThresholdEntryIndex  OBJECT-TYPE
                                  SYNTAX  INTEGER(0..255)
                                  ACCESS  read-only
                                  STATUS  mandatory
                                  DESCRIPTION
                                  "Index for CPUx threshold entry."
                                  ::= { cpuTempThresholdsEntry 1 }

        cpuTempThresholdEntryName  OBJECT-TYPE
                                  SYNTAX  OCTET STRING (SIZE(0..16))
                                  ACCESS  read-only
                                  STATUS  mandatory
                                  DESCRIPTION
                                  "CPUx threshold entry null terminated string that
                                  contains the CPU name, for example 'CPU-1'."
                                  ::= { cpuTempThresholdsEntry 2 }

        cpuTempThresholdEntryCurrentValue OBJECT-TYPE
                                    SYNTAX  OCTET STRING
                                    ACCESS  read-only
                                    STATUS  mandatory
                                    DESCRIPTION
                                    "CPUx temperature in degrees centigrade(C).
                                    An octet string expressed as 'sddd.dd Centigrade' where:
                                    s is the sign ('-' for negative or blank space for positive)
                                    d is a decimal digit or blank space for a leading zero.
                                    The string 'Not Readable!' indicates that the given monitor
                                    is not supported on this system."
                                    ::= { cpuTempThresholdsEntry 3 }

        cpuTempThresholdEntryHardShutdownValue OBJECT-TYPE
                                    SYNTAX  OCTET STRING
                                    ACCESS  read-only
                                    STATUS  mandatory
                                    DESCRIPTION
                                    "CPUx temperature in degrees centigrade(C).
                                    If the component's temperature rises above this value the
                                    system will be powered off immediately.
                                    If enabled, a critical alert/event will be generated.
                                    An octet string expressed as 'sddd.dd Centigrade' where:
                                    s is the sign ('-' for negative or blank space for positive)
                                    d is a decimal digit or blank space for a leading zero.
                                    The string 'Not Readable!' indicates that the given monitor
                                    is not supported on this system."
                                    ::= { cpuTempThresholdsEntry 4 }



        cpuTempThresholdEntrySoftShutdownValue OBJECT-TYPE
                                    SYNTAX  OCTET STRING
                                    ACCESS  read-only
                                    STATUS  mandatory
                                    DESCRIPTION
                                    "CPUx temperature in degrees centigrade(C).
                                    If the component's temperature rises above this value the
                                    system will be powered off after the O/S is shut down.
                                    If enabled, a critical alert/event is generated.
                                    An octet string expressed as 'sddd.dd Centigrade' where:
                                    s is the sign ('-' for negative or blank space for positive)
                                    d is a decimal digit or blank space for a leading zero.
                                    The string 'Not Readable!' indicates that the given monitor
                                    is not supported on this system."
                                    ::= { cpuTempThresholdsEntry 5 }


        cpuTempThresholdEntryWarningValue OBJECT-TYPE
                                    SYNTAX  OCTET STRING
                                    ACCESS  read-only
                                    STATUS  mandatory
                                    DESCRIPTION
                                    "CPUx temperature in degrees centigrade(C).
                                    If the temperature rises above this value a warning alert/event
                                    if enabled will be generated.
                                    An octet string expressed as 'sddd.dd Centigrade' where:
                                    s is the sign ('-' for negative or blank space for positive)
                                    d is a decimal digit or blank space for a leading zero.
                                    The string 'Not Readable!' indicates that the given monitor
                                    is not supported on this system."
                                    ::= { cpuTempThresholdsEntry 6 }

        cpuTempThresholdEntryWarningResetValue OBJECT-TYPE
                                    SYNTAX  OCTET STRING
                                    ACCESS  read-only
                                    STATUS  mandatory
                                    DESCRIPTION
                                    "CPUx temperature in degrees centigrade(C).
                                    If the temperature rises above this value and
                                    if a warning alert/event had previously been
                                    created then the alert/event will be reset.
                                    An octet string expressed as 'sddd.dd Centigrade' where:
                                    s is the sign ('-' for negative or blank space for positive)
                                    d is a decimal digit or blank space for a leading zero.
                                    The string 'Not Readable!' indicates that the given monitor
                                    is not supported on this system."
                                    ::= { cpuTempThresholdsEntry 7 }


       -- ***********************************************************************
       -- DASD X Temperature Thresholds
       -- ***********************************************************************

       dasdXTempThresholds OBJECT IDENTIFIER ::= { tempThresholds 6 }


        dasdTempThresholdsTable  OBJECT-TYPE
                              SYNTAX  SEQUENCE OF DasdTempThresholdsEntry
                              ACCESS  not-accessible
                              STATUS  mandatory
                              DESCRIPTION
                              "Table of DASD threshold entries"
                              ::= {  dasdXTempThresholds 1 }

        dasdTempThresholdsEntry  OBJECT-TYPE
                              SYNTAX  DasdTempThresholdsEntry
                              ACCESS  not-accessible
                              STATUS  mandatory
                              DESCRIPTION
                              "DASD temperature threshold entries"
                              INDEX { dasdTempThresholdEntryIndex }
                              ::= { dasdTempThresholdsTable 1 }

        DasdTempThresholdsEntry ::= SEQUENCE {
                     dasdTempThresholdEntryIndex INTEGER(0..255),
                     dasdTempThresholdEntryName OCTET STRING (SIZE(0..16)),
                     dasdTempThresholdEntryCurrentValue OCTET STRING,
                     dasdTempThresholdEntryHardShutdownValue OCTET STRING,
                     dasdTempThresholdEntrySoftShutdownValue OCTET STRING,
                     dasdTempThresholdEntryWarningValue OCTET STRING,
                     dasdTempThresholdEntryWarningResetValue OCTET STRING
        }


        dasdTempThresholdEntryIndex  OBJECT-TYPE
                                  SYNTAX  INTEGER(0..255)
                                  ACCESS  read-only
                                  STATUS  mandatory
                                  DESCRIPTION
                                  "Index for DASDx threshold entry."
                                  ::= { dasdTempThresholdsEntry 1 }

        dasdTempThresholdEntryName  OBJECT-TYPE
                                  SYNTAX  OCTET STRING (SIZE(0..16))
                                  ACCESS  read-only
                                  STATUS  mandatory
                                  DESCRIPTION
                                  "DASDx threshold entry null terminated string that
                                  contains the DASD name, for example 'DASD-1'."
                                  ::= { dasdTempThresholdsEntry 2 }

        dasdTempThresholdEntryCurrentValue OBJECT-TYPE
                                    SYNTAX  OCTET STRING
                                    ACCESS  read-only
                                    STATUS  mandatory
                                    DESCRIPTION
                                    "DASDx temperature in degrees centigrade(C).
                                    An octet string expressed as 'sddd.dd Centigrade' where:
                                    s is the sign ('-' for negative or blank space for positive)
                                    d is a decimal digit or blank space for a leading zero.
                                    The string 'Not Readable!' indicates that the given monitor
                                    is not supported on this system."
                                    ::= { dasdTempThresholdsEntry 3 }

        dasdTempThresholdEntryHardShutdownValue OBJECT-TYPE
                                    SYNTAX  OCTET STRING
                                    ACCESS  read-only
                                    STATUS  mandatory
                                    DESCRIPTION
                                    "DASDx temperature in degrees centigrade(C).
                                    If the component's temperature rises above this value the
                                    system will be powered off immediately.
                                    If enabled, a critical alert/event will be generated.
                                    An octet string expressed as 'sddd.dd Centigrade' where:
                                    s is the sign ('-' for negative or blank space for positive)
                                    d is a decimal digit or blank space for a leading zero.
                                    The string 'Not Readable!' indicates that the given monitor
                                    is not supported on this system."
                                    ::= { dasdTempThresholdsEntry 4 }



        dasdTempThresholdEntrySoftShutdownValue OBJECT-TYPE
                                    SYNTAX  OCTET STRING
                                    ACCESS  read-only
                                    STATUS  mandatory
                                    DESCRIPTION
                                    "DASDx temperature in degrees centigrade(C).
                                    If the component's temperature rises above this value the
                                    system will be powered off after the O/S is shut down.
                                    If enabled, a critical alert/event is generated.
                                    An octet string expressed as 'sddd.dd Centigrade' where:
                                    s is the sign ('-' for negative or blank space for positive)
                                    d is a decimal digit or blank space for a leading zero.
                                    The string 'Not Readable!' indicates that the given monitor
                                    is not supported on this system."
                                    ::= { dasdTempThresholdsEntry 5 }


        dasdTempThresholdEntryWarningValue OBJECT-TYPE
                                    SYNTAX  OCTET STRING
                                    ACCESS  read-only
                                    STATUS  mandatory
                                    DESCRIPTION
                                    "DASDx temperature in degrees centigrade(C).
                                    If the temperature rises above this value a warning alert/event
                                    if enabled will be generated.
                                    An octet string expressed as 'sddd.dd Centigrade' where:
                                    s is the sign ('-' for negative or blank space for positive)
                                    d is a decimal digit or blank space for a leading zero.
                                    The string 'Not Readable!' indicates that the given monitor
                                    is not supported on this system."
                                    ::= { dasdTempThresholdsEntry 6 }

        dasdTempThresholdEntryWarningResetValue OBJECT-TYPE
                                    SYNTAX  OCTET STRING
                                    ACCESS  read-only
                                    STATUS  mandatory
                                    DESCRIPTION
                                    "DASDx temperature in degrees centigrade(C).
                                    If the temperature rises above this value and
                                    if a warning alert/event had previously been
                                    created then the alert/event will be reset.
                                    An octet string expressed as 'sddd.dd Centigrade' where:
                                    s is the sign ('-' for negative or blank space for positive)
                                    d is a decimal digit or blank space for a leading zero.
                                    The string 'Not Readable!' indicates that the given monitor
                                    is not supported on this system."
                                    ::= { dasdTempThresholdsEntry 7 }

      -- ***********************************************************************
      -- Voltage Thresholds
      -- ***********************************************************************
      voltageThresholds  OBJECT IDENTIFIER ::= { monitorThresholds 2 }

       voltageThresholdsTable  OBJECT-TYPE
                             SYNTAX  SEQUENCE OF VoltageThresholdsEntry
                             ACCESS  not-accessible
                             STATUS  mandatory
                             DESCRIPTION
                             "Table of voltage threshold entries"
                             ::= {  voltageThresholds 1 }

       voltageThresholdsEntry  OBJECT-TYPE
                             SYNTAX VoltageThresholdsEntry
                             ACCESS  not-accessible
                             STATUS  mandatory
                             DESCRIPTION
                             "Voltage threshold entries"
                             INDEX { voltageThresholdEntryIndex }
                             ::= { voltageThresholdsTable 1 }

       VoltageThresholdsEntry ::= SEQUENCE {
                    voltageThresholdEntryIndex INTEGER(0..255),
                    voltageThresholdEntryName OCTET STRING (SIZE(0..16)),
                    voltageThresholdEntryCurrentValue OCTET STRING,
                    voltageThresholdEntryHardShutdownHighValue OCTET STRING,
                    voltageThresholdEntrySoftShutdownHighValue OCTET STRING,
                    voltageThresholdEntryWarningHighValue OCTET STRING,
                    voltageThresholdEntryWarningResetHighValue OCTET STRING,
                    voltageThresholdEntryHardShutdownLowValue OCTET STRING,
                    voltageThresholdEntrySoftShutdownLowValue OCTET STRING,
                    voltageThresholdEntryWarningLowValue OCTET STRING,
                    voltageThresholdEntryWarningResetLowValue OCTET STRING
       }


       voltageThresholdEntryIndex  OBJECT-TYPE
                                 SYNTAX  INTEGER(0..255)
                                 ACCESS  read-only
                                 STATUS  mandatory
                                 DESCRIPTION
                                 "Index for voltage threshold entry."
                                 ::= { voltageThresholdsEntry 1 }

       voltageThresholdEntryName  OBJECT-TYPE
                                 SYNTAX  OCTET STRING (SIZE(0..16))
                                 ACCESS  read-only
                                 STATUS  mandatory
                                 DESCRIPTION
                                 "Voltage threshold entry null terminated string that
                                 contains the power supply's name, for example '+5V'."
                                 ::= { voltageThresholdsEntry 2 }

       voltageThresholdEntryCurrentValue OBJECT-TYPE
                                   SYNTAX  OCTET STRING
                                   ACCESS  read-only
                                   STATUS  mandatory
                                   DESCRIPTION
                                   "Voltage reading expressed in Volts(V).
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 3 }

       voltageThresholdEntryHardShutdownHighValue OBJECT-TYPE
                                   SYNTAX  OCTET STRING
                                   ACCESS  read-only
                                   STATUS  mandatory
                                   DESCRIPTION
                                   "Voltage threshold reading expressed in Volts(V).
                                   If the voltage rises above this value the
                                   system will be powered off immediately.
                                   If enabled, a critical alert/event will be generated.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 4 }

       voltageThresholdEntrySoftShutdownHighValue OBJECT-TYPE
                                   SYNTAX  OCTET STRING
                                   ACCESS  read-only
                                   STATUS  mandatory
                                   DESCRIPTION
                                   "Voltage threshold reading expressed in Volts(V).
                                   If the voltage rises above this value the system will be powered off
                                   after the O/S is shut down.
                                   If enabled a critical alert/event is generated.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 5 }

       voltageThresholdEntryWarningHighValue OBJECT-TYPE
                                   SYNTAX  OCTET STRING
                                   ACCESS  read-only
                                   STATUS  mandatory
                                   DESCRIPTION
                                   "Voltage threshold reading expressed in Volts(V).
                                   If the voltage rises above this value a warning alert/event
                                   if enabled will be generated.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 6 }

       voltageThresholdEntryWarningResetHighValue OBJECT-TYPE
                                   SYNTAX  OCTET STRING
                                   ACCESS  read-only
                                   STATUS  mandatory
                                   DESCRIPTION
                                   "Voltage threshold reading expressed in Volts(V).
                                   If the voltage rises above this value and
                                   if a warning alert/event had previously been
                                   created then the alert/event will be reset.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 7 }


       voltageThresholdEntryHardShutdownLowValue OBJECT-TYPE
                                   SYNTAX  OCTET STRING
                                   ACCESS  read-only
                                   STATUS  mandatory
                                   DESCRIPTION
                                   "Voltage threshold reading expressed in Volts(V).
                                   If the voltage drops below this value the
                                   system will be powered off immediately.
                                   If enabled, a critical alert/event will be generated.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 8 }

       voltageThresholdEntrySoftShutdownLowValue OBJECT-TYPE
                                   SYNTAX  OCTET STRING
                                   ACCESS  read-only
                                   STATUS  mandatory
                                   DESCRIPTION
                                   "Voltage threshold reading expressed in Volts(V).
                                   If the voltage drops below this value the system will be powered off
                                   after the O/S is shut down.
                                   If enabled a critical alert/event is generated.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 9 }

       voltageThresholdEntryWarningLowValue OBJECT-TYPE
                                   SYNTAX  OCTET STRING
                                   ACCESS  read-only
                                   STATUS  mandatory
                                   DESCRIPTION
                                   "Voltage threshold reading expressed in Volts(V).
                                   If the voltage drops below this value a warning alert/event
                                   if enabled will be generated.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 10 }

       voltageThresholdEntryWarningResetLowValue OBJECT-TYPE
                                   SYNTAX  OCTET STRING
                                   ACCESS  read-only
                                   STATUS  mandatory
                                   DESCRIPTION
                                   "Voltage threshold reading expressed in Volts(V).
                                   If the voltage drops below this value and
                                   if a warning alert/event had previously been
                                   created then the alert/event will be reset.
                                   An octet string expressed as 'sdd.dd Volts' where:
                                   s is the sign ('-' for negative or '+' for positive)
                                   d is a decimal digit or blank space for a leading zero.
                                   The string 'Not Readable!' indicates that the given monitor
                                   is not supported on this system."
                                   ::= { voltageThresholdsEntry 11 }


     -- ***********************************************************************
     -- Vital Product Data(VPD) information
     -- ***********************************************************************
     vpdInformation  OBJECT IDENTIFIER ::= { monitors 21 }

      -- ***********************************************************************
      -- System Firmware Level VPD
      -- ***********************************************************************
      systemFirmwareVpd OBJECT IDENTIFIER ::= { vpdInformation 1 }

       -- ***********************************************************************
       -- BIOS Firmware Level VPD
       -- ***********************************************************************
       biosVpd OBJECT IDENTIFIER ::= { systemFirmwareVpd 1 }

        biosVpdVersionNumber OBJECT-TYPE
                      SYNTAX  OCTET STRING
                      ACCESS  read-only
                      STATUS  mandatory
                      DESCRIPTION
                      "Bios firmware version number (from System BIOS)."
                      ::= { biosVpd 1 }

        biosVpdBuildLevelName OBJECT-TYPE
                      SYNTAX  OCTET STRING
                      ACCESS  read-only
                      STATUS  mandatory
                      DESCRIPTION
                      "Bios firmware build level name (from System BIOS)."
                      ::= { biosVpd 2 }

        biosVpdBuildDate OBJECT-TYPE
                      SYNTAX  OCTET STRING
                      ACCESS  read-only
                      STATUS  mandatory
                      DESCRIPTION
                      "Bios firmware build date (from System BIOS)."
                      ::= { biosVpd 3 }


--       ***********************************************************************
--       ** DIAG Firmware Level VPD
--       ***********************************************************************
--       diagVpd OBJECT IDENTIFIER ::= { systemFirmwareVpd 2 }
--
--        diagVpdVersionNumber OBJECT-TYPE
--                      SYNTAX  OCTET STRING
--                      ACCESS  read-only
--                      STATUS  mandatory
--                      DESCRIPTION
--                      "Diagnostics firmware version number (from System BIOS)."
--                      ::= { diagVpd 1 }
--
--        diagVpdBuildLevelName OBJECT-TYPE
--                      SYNTAX  OCTET STRING
--                      ACCESS  read-only
--                      STATUS  mandatory
--                      DESCRIPTION
--                      "Diagnostics firmware build level name (from System BIOS)."
--                      ::= { diagVpd 2 }
--
--        diagVpdBuildDate OBJECT-TYPE
--                      SYNTAX  OCTET STRING
--                      ACCESS  read-only
--                      STATUS  mandatory
--                      DESCRIPTION
--                      "Diagnostics firmware build date (from System BIOS)."
--                      ::= { diagVpd 3 }


       -- ***********************************************************************
       -- Power backplane firmware VPD
       -- ***********************************************************************
       powerBackplaneFirmwareVpd OBJECT IDENTIFIER ::= { systemFirmwareVpd 15 }

        powerBackplaneRevisionNumber OBJECT-TYPE
                      SYNTAX  OCTET STRING
                      ACCESS  read-only
                      STATUS  mandatory
                      DESCRIPTION
                      "Power Backplane firmware revison number."
                      ::= { powerBackplaneFirmwareVpd 1 }


       -- ***********************************************************************
       -- Integrated system management processor VPD
       -- ***********************************************************************
       ismpFirmwareVpd OBJECT IDENTIFIER ::= { systemFirmwareVpd 19 }

        ismpRevisionNumber OBJECT-TYPE
                      SYNTAX  OCTET STRING
                      ACCESS  read-only
                      STATUS  mandatory
                      DESCRIPTION
                      "ISMP firmware revison number."
                      ::= { ismpFirmwareVpd 1 }


      -- ***********************************************************************
      -- ASM VPD Video BIOS
      -- ***********************************************************************
      spVpdVideoBios OBJECT IDENTIFIER ::= { systemFirmwareVpd 20 }

       asmVideoBios OBJECT-TYPE
                     SYNTAX  OCTET STRING
                     ACCESS  read-only
                     STATUS  mandatory
                     DESCRIPTION
                     "ASM VPD Video Bios."
                     ::= { spVpdVideoBios 1 }

      -- ***********************************************************************
      -- ASM VPD Device Driver
      -- ***********************************************************************
      spVpdDeviceDriver OBJECT IDENTIFIER ::= { systemFirmwareVpd 21 }

       asmDeviceDriver OBJECT-TYPE
                     SYNTAX  OCTET STRING
                     ACCESS  read-only
                     STATUS  mandatory
                     DESCRIPTION
                     "ASM VPD Device Driver."
                     ::= { spVpdDeviceDriver 1 }

      -- ***********************************************************************
      -- Machine Level VPD
      -- ***********************************************************************
      machineVpd OBJECT IDENTIFIER ::= { vpdInformation 2 }


       machineLevelVpd OBJECT IDENTIFIER ::= { machineVpd 1 }

        machineLevelVpdMachineType OBJECT-TYPE
                      SYNTAX  OCTET STRING
                      ACCESS  read-only
                      STATUS  mandatory
                      DESCRIPTION
                      "Machine type VPD information(from System BIOS)."
                      ::= { machineLevelVpd 1 }

        machineLevelVpdMachineModel OBJECT-TYPE
                      SYNTAX  OCTET STRING
                      ACCESS  read-only
                      STATUS  mandatory
                      DESCRIPTION
                      "Machine model VPD information(from System BIOS)."
                      ::= { machineLevelVpd 2 }

        machineLevelSerialNumber OBJECT-TYPE
                      SYNTAX  OCTET STRING
                      ACCESS  read-only
                      STATUS  mandatory
                      DESCRIPTION
                      "Machine serial number VPD information(from System BIOS)."
                      ::= { machineLevelVpd 3 }

        machineLevelUUID OBJECT-TYPE
                      SYNTAX  OCTET STRING
                      ACCESS  read-only
                      STATUS  mandatory
                      DESCRIPTION
                      "Machine UUID(Universal Unique ID information) (from System BIOS)."
                      ::= { machineLevelVpd 4 }

      -- ***********************************************************************
      -- SP Firmware VPD
      -- ***********************************************************************
      spFirmwareVpdTable OBJECT-TYPE
                    SYNTAX  SEQUENCE OF SpFirmwareVpdEntry
                    ACCESS  not-accessible
                    STATUS  mandatory
                    DESCRIPTION
                    "Table of SP Firmware VPD."
                    ::= { vpdInformation 6 }

      spFirmwareVpdEntry OBJECT-TYPE
                    SYNTAX SpFirmwareVpdEntry
                    ACCESS  not-accessible
                    STATUS  mandatory
                    DESCRIPTION
                    "SP Firmware VPD entry."
                    INDEX { firmwareVpdIndex }
                    ::= { spFirmwareVpdTable 1 }


      SpFirmwareVpdEntry ::= SEQUENCE {
                  firmwareVpdIndex INTEGER,
                  firmwareVpdName OCTET STRING,
                  firmwareVpdBuildId OCTET STRING,
                  firmwareVpdRevisonNumber OCTET STRING,
                  firmwareVpdFilename OCTET STRING,
                  firmwareVpdBuildDate OCTET STRING
      }


      firmwareVpdIndex  OBJECT-TYPE
                  SYNTAX  INTEGER
                  ACCESS  read-only
                  STATUS  mandatory
                  DESCRIPTION
                  "Firmware VPD index."
                  ::= { spFirmwareVpdEntry 1 }

      firmwareVpdName  OBJECT-TYPE
                  SYNTAX  OCTET STRING
                  ACCESS  read-only
                  STATUS  mandatory
                  DESCRIPTION
                  "Firmware VPD name description."
                  ::= { spFirmwareVpdEntry 2 }

      firmwareVpdBuildId  OBJECT-TYPE
                  SYNTAX  OCTET STRING
                  ACCESS  read-only
                  STATUS  mandatory
                  DESCRIPTION
                  "Firmware VPD build identification."
                  ::= { spFirmwareVpdEntry 3 }

      firmwareVpdRevisonNumber  OBJECT-TYPE
                  SYNTAX  OCTET STRING
                  ACCESS  read-only
                  STATUS  mandatory
                  DESCRIPTION
                  "Firmware VPD revision number."
                  ::= { spFirmwareVpdEntry 4 }

      firmwareVpdFilename  OBJECT-TYPE
                  SYNTAX  OCTET STRING
                  ACCESS  read-only
                  STATUS  mandatory
                  DESCRIPTION
                  "Firmware VPD file name."
                  ::= { spFirmwareVpdEntry 5 }

      firmwareVpdBuildDate  OBJECT-TYPE
                  SYNTAX  OCTET STRING
                  ACCESS  read-only
                  STATUS  mandatory
                  DESCRIPTION
                  "Firmware VPD build date."
                  ::= { spFirmwareVpdEntry 6 }

      -- ***********************************************************************
      -- System Component Level VPD
      -- ***********************************************************************
      systemComponentLevelVpdTable OBJECT-TYPE
                    SYNTAX  SEQUENCE OF SystemComponentLevelVpdEntry
                    ACCESS  not-accessible
                    STATUS  mandatory
                    DESCRIPTION
                    "Table of the system component hardware VPD information.  View as a
                    table and not as individual entries for consistent results."
                    ::= { vpdInformation 17 }

      systemComponentLevelVpdEntry OBJECT-TYPE
                    SYNTAX SystemComponentLevelVpdEntry
                    ACCESS  not-accessible
                    STATUS  mandatory
                    DESCRIPTION
                    "System component hardware VPD entry.  View as a table and not as
                    individual entries for consistent results."
                    INDEX { componentLevelVpdIndex }
                    ::= { systemComponentLevelVpdTable 1 }

      SystemComponentLevelVpdEntry ::= SEQUENCE {
                  componentLevelVpdIndex INTEGER,
                  componentLevelVpdFruNumber OCTET STRING,
                  componentLevelVpdSerialNumber OCTET STRING,
                  componentLevelVpdManufacturingId OCTET STRING,
                  componentLevelVpdSlotNumber OCTET STRING
      }

      componentLevelVpdIndex  OBJECT-TYPE
                  SYNTAX  INTEGER
                  ACCESS  read-only
                  STATUS  mandatory
                  DESCRIPTION
                  "System component level VPD index.  View as a table and not as individual
                  entries for consistent results."
                  ::= { systemComponentLevelVpdEntry 1 }

      componentLevelVpdFruNumber  OBJECT-TYPE
                  SYNTAX  OCTET STRING
                  ACCESS  read-only
                  STATUS  mandatory
                  DESCRIPTION
                  "System component level VPD FRU number.  View as a table and not as
                  individual entries for consistent results."
                  ::= { systemComponentLevelVpdEntry 2 }

      componentLevelVpdSerialNumber  OBJECT-TYPE
                  SYNTAX  OCTET STRING
                  ACCESS  read-only
                  STATUS  mandatory
                  DESCRIPTION
                  "System component level VPD serial number.  View as a table and not as
                  individual entries for consistent results."
                  ::= { systemComponentLevelVpdEntry 3 }

      componentLevelVpdManufacturingId  OBJECT-TYPE
                  SYNTAX  OCTET STRING
                  ACCESS  read-only
                  STATUS  mandatory
                  DESCRIPTION
                  "System component level VPD manufacturing ID.  View as a table and not as
                  individual entries for consistent results."
                  ::= { systemComponentLevelVpdEntry 4 }

      componentLevelVpdSlotNumber  OBJECT-TYPE
                  SYNTAX  OCTET STRING
                  ACCESS  read-only
                  STATUS  mandatory
                  DESCRIPTION
                  "System component level VPD Slot number.  View as a table and not as
                  individual entries for consistent results."
                  ::= { systemComponentLevelVpdEntry 5 }

      -- ***********************************************************************
      -- System Component Level VPD Tracking log
      -- ***********************************************************************
      systemComponentLevelVpdTrackingTable OBJECT-TYPE
                    SYNTAX  SEQUENCE OF SystemComponentLevelVpdTrackingEntry
                    ACCESS  not-accessible
                    STATUS  mandatory
                    DESCRIPTION
                    "Table of system component hardware VPD tracking activity log.  View as
                    a table and not as individual entries for consistent results."
                    ::= { vpdInformation 18 }

      systemComponentLevelVpdTrackingEntry OBJECT-TYPE
                    SYNTAX SystemComponentLevelVpdTrackingEntry
                    ACCESS  not-accessible
                    STATUS  mandatory
                    DESCRIPTION
                    "System component hardware VPD tracking activity log entry.  View as a
                    table and not as individual entries for consistent results."
                    INDEX { componentLevelVpdTrackingIndex }
                    ::= { systemComponentLevelVpdTrackingTable 1 }

      SystemComponentLevelVpdTrackingEntry ::= SEQUENCE {
                  componentLevelVpdTrackingIndex INTEGER,
                  componentLevelVpdTrackingFruNumber OCTET STRING,
                  componentLevelVpdTrackingSerialNumber OCTET STRING,
                  componentLevelVpdTrackingManufacturingId OCTET STRING,
                  componentLevelVpdTrackingSlotNumber OCTET STRING,
                  componentLevelVpdTrackingAction OCTET STRING,
                  componentLevelVpdTrackingTimestamp OCTET STRING

      }

      componentLevelVpdTrackingIndex  OBJECT-TYPE
                  SYNTAX  INTEGER
                  ACCESS  read-only
                  STATUS  mandatory
                  DESCRIPTION
                  "System component level VPD tracking activity log index.  View as a table
                  and not as individual entries for consistent results."
                  ::= { systemComponentLevelVpdTrackingEntry 1 }

      componentLevelVpdTrackingFruNumber  OBJECT-TYPE
                  SYNTAX  OCTET STRING
                  ACCESS  read-only
                  STATUS  mandatory
                  DESCRIPTION
                  "System component level VPD tracking activity log FRU number.  View as a
                  table and not as individual entries for consistent results."
                  ::= { systemComponentLevelVpdTrackingEntry 2 }

      componentLevelVpdTrackingSerialNumber  OBJECT-TYPE
                  SYNTAX  OCTET STRING
                  ACCESS  read-only
                  STATUS  mandatory
                  DESCRIPTION
                  "System component level VPD tracking activity log serial number.  View as
                  a table and not as individual entries for consistent results."
                  ::= { systemComponentLevelVpdTrackingEntry 3 }

      componentLevelVpdTrackingManufacturingId  OBJECT-TYPE
                  SYNTAX  OCTET STRING
                  ACCESS  read-only
                  STATUS  mandatory
                  DESCRIPTION
                  "System component level VPD tracking activity log manufacturing ID.  View
                  as a table and not as individual entries for consistent results."
                  ::= { systemComponentLevelVpdTrackingEntry 4 }

      componentLevelVpdTrackingSlotNumber  OBJECT-TYPE
                  SYNTAX  OCTET STRING
                  ACCESS  read-only
                  STATUS  mandatory
                  DESCRIPTION
                  "System component level VPD tracking activity log Slot number.  View as a
                  table and not as individual entries for consistent results."
                  ::= { systemComponentLevelVpdTrackingEntry 5 }

      componentLevelVpdTrackingAction  OBJECT-TYPE
                  SYNTAX  OCTET STRING
                  ACCESS  read-only
                  STATUS  mandatory
                  DESCRIPTION
                  "System component level VPD tracking activity log action(added/removed).
                  View as a table and not as individual entries for consistent results."
                  ::= {systemComponentLevelVpdTrackingEntry 6 }

      componentLevelVpdTrackingTimestamp  OBJECT-TYPE
                  SYNTAX  OCTET STRING
                  ACCESS  read-only
                  STATUS  mandatory
                  DESCRIPTION
                  "System component level VPD tracking activity log timestanp.
                  View as a table and not as individual entries for consistent results."
                  ::= { systemComponentLevelVpdTrackingEntry 7 }



-- ***********************************************************************
--  Error Log Information
-- ***********************************************************************
    -- ***********************************************************************
    -- Event Log Information
    -- ***********************************************************************
    eventLog   OBJECT IDENTIFIER ::= { errorLogs 4 }

     eventLogTable OBJECT-TYPE
                    SYNTAX  SEQUENCE OF EventLogEntry
                    ACCESS  not-accessible
                    STATUS  mandatory
                    DESCRIPTION
                    "Table of event logs.  View as a table and not as individual entries
                    for consistent results."
                    ::= { eventLog 2 }

     eventLogEntry OBJECT-TYPE
                    SYNTAX EventLogEntry
                    ACCESS  not-accessible
                    STATUS  mandatory
                    DESCRIPTION
                    "Event log entries.  View as a table and not as individual entries for
                    consistent results."
                    INDEX { eventLogIndex }
                    ::= { eventLogTable 1 }


     EventLogEntry ::= SEQUENCE {
                  eventLogIndex INTEGER,
                  eventLogString OCTET STRING
     }


     eventLogIndex   OBJECT-TYPE
                  SYNTAX  INTEGER
                  ACCESS  read-only
                  STATUS  mandatory
                  DESCRIPTION
                  "Event log index number. View as a table and not as individual entries for
                  consistent results."
                  ::= { eventLogEntry 1 }

     eventLogString OBJECT-TYPE
                  SYNTAX  OCTET STRING
                  ACCESS  read-only
                  STATUS  mandatory
                  DESCRIPTION
                  "Contains a string of information to detail the event.  View as a table and
                  not as individual entries for consistent results."
                  ::= { eventLogEntry 2}


     eventLogClr    OBJECT-TYPE
                  SYNTAX  INTEGER {
                    execute(1)
                   }
                  ACCESS  write-only
                  STATUS  mandatory
                  DESCRIPTION
                  "Clear the event log."
                  ::= { eventLog 3 }


-- ***********************************************************************
--  Configure the ASM
-- ***********************************************************************
    -- ***********************************************************************
    -- Remote Access Configuration
    -- ***********************************************************************
    remoteAccessConfig  OBJECT IDENTIFIER ::= { configureSP 1 }

     -- ***********************************************************************
     -- General Remote Access and Remote Alerts Configuration
     -- ***********************************************************************
     generalRemoteCfg    OBJECT IDENTIFIER ::= { remoteAccessConfig 1 }

      dialInEnabled   OBJECT-TYPE
                   SYNTAX  INTEGER {
                     false(0),
                     true(1)
                   }
                   ACCESS  read-write
                   STATUS  mandatory
                   DESCRIPTION
                   "If true(1) then the setting is enabled and the remote
                   client is allowed to dial into the ASM.
                   This must be enabled for a dial-in from any serial
                   connection: null modem, modem or PPP.

                   Note: ASM on some servers does not have serial port support."
                   ::= { generalRemoteCfg 1 }

      dedicateSharedSerialPortToSp OBJECT-TYPE
                   SYNTAX  INTEGER {
                     false(0),
                     true(1)
                   }
                   ACCESS  read-write
                   STATUS  mandatory
                   DESCRIPTION
                   "If true(1) then the setting is enabled and the
                   serial port that can be shared with the host system
                   is dedicated to the ASM. Setting this
                   will take effect on the next restart of the ASM.

                   Note: ASM on some servers does not have serial port support."
                   ::= { generalRemoteCfg 2 }

      remoteAlertRetryDelay OBJECT-TYPE
                   SYNTAX  INTEGER {
                     noDelay(0),
                     oneHalfMinute(30),
                     oneMinute(60),
                     oneAndHalfMinutes(90),
                     twoMinutes(120),
                     twoAndHalfMinutes(150),
                     threeMinutes(180),
                     threeAndHalfMinutes(210),
                     fourMinutes(240)
                   }
                   ACCESS  read-write
                   STATUS  mandatory
                   DESCRIPTION
                   "Number in seconds to delay between retries if sending a
                   remote alert is unsuccessful."
                   ::= { generalRemoteCfg 3 }

      remoteAlertRetryCount OBJECT-TYPE
                   SYNTAX  INTEGER {
                     noretry(0),
                     retry1(1),
                     retry2(2),
                     retry3(3),
                     retry4(4),
                     retry5(5),
                     retry6(6),
                     retry7(7),
                     retry8(8)
                   }
                   ACCESS  read-write
                   STATUS  mandatory
                   DESCRIPTION
                   "Number of additional times a remote alert will be
                   retried if not succesfully sent. A value of zero indicates
                   no retries will be attempted."
                   ::= { generalRemoteCfg 4 }

      remoteAlertEntryDelay OBJECT-TYPE
                   SYNTAX  INTEGER {
                     noDelay(0),
                     oneHalfMinute(30),
                     oneMinute(60),
                     oneAndHalfMinutes(90),
                     twoMinutes(120),
                     twoAndHalfMinutes(150),
                     threeMinutes(180),
                     threeAndHalfMinutes(210),
                     fourMinutes(240)
                   }
                   ACCESS  read-write
                   STATUS  mandatory
                   DESCRIPTION
                   "Number in seconds to delay between entries if sending a
                   remote alert is unsuccessful."
                   ::= { generalRemoteCfg 5 }

      remoteAccessTamperDelay OBJECT-TYPE
                   SYNTAX  INTEGER {
                     nowait(0),
                     oneMinute(1),
                     twoMinutes(2),
                     threeMinutes(3),
                     fourMinutes(4),
                     fiveMinutes(5),
                     sixMinutes(6),
                     sevenMinutes(7),
                     tenMinutes(10),
                     fifteenMinutes(15),
                     twentyMinutes(20),
                     thirtyMinutes(30),
                     sixtyMinutes(60),
                     oneTwentyMinutes(120),
                     oneEightyMinutes(180),
                     twoFortyMinutes(240)
                   }
                   ACCESS  read-write
                   STATUS  mandatory
                   DESCRIPTION
                   "Number in minutes to prohibit a remote login attempt
                   after more than 5 sequential login attempts have failed."
                   ::= { generalRemoteCfg 6 }

      userAuthenticationMethod OBJECT-TYPE
                    SYNTAX  INTEGER {
                       localOnly(0),
                       ldapOnly(1),
                       localFirstThenLdap(2),
                       ldapFirstThenLocal(3)
                    }
                    ACCESS  read-write
                    STATUS  mandatory
                    DESCRIPTION
                    "Use this field to specify how users attempting to login should be authenticated.
                    There are two methods:
                       Local authentication. Userid and password are verified by searching the list
                          of users locally configured under Local Login Profiles.
                       LDAP based authentication. Users are authenticated via a remote LDAP server.
                    One or both authentication methods can be selected. If both methods should be
                    used, the order must be specified."
                   ::= { generalRemoteCfg 7 }

      allowModemLogin OBJECT-TYPE
                    SYNTAX  INTEGER {
                       disabled(0),
                       enabled(1)
                    }
                    ACCESS  read-write
                    STATUS  mandatory
                    DESCRIPTION
                    "Allow the user login through modem connection.

                    Note: ASM on some servers does not have serial port support."
                   ::= { generalRemoteCfg 8 }

      webInactivityTimeout OBJECT-TYPE
                    SYNTAX  INTEGER {
                       oneMinutes(0),
                       fiveMinutes(1),
                       tenMinutes(2),
                       fifteenMinutes(3),
                       twentyMinutes(4),
                       noTimeout(5),
                       userPicksTimeout(6)
                    }
                    ACCESS  read-write
                    STATUS  mandatory
                    DESCRIPTION
                    "Use this field to indicate how long, in minutes, the ASM subsystem will wait
                    before disconnecting an inactive web session. Select the no timeout option to
                    disable this feature. Select the User picks timeout option if the timeout should
                    instead be selected by the user during the login process."
                   ::= { generalRemoteCfg 9 }

           -- begin account security management
       customSecuritySettings OBJECT IDENTIFIER ::= { generalRemoteCfg 20 }

           loginPasswordRequired OBJECT-TYPE
                   SYNTAX  INTEGER {
                     disabled(0),
                     enabled(1)
                   }
                   ACCESS  read-write
                   STATUS  mandatory
                   DESCRIPTION
                   "If enabled, all users require a login password to access the AMM
                   via the CLI and Web interfaces.  The default value is disabled."
                   ::= { customSecuritySettings 1 }

           passwordExpirationPeriod OBJECT-TYPE
                   SYNTAX  INTEGER
                   ACCESS  read-write
                   STATUS  mandatory
                   DESCRIPTION
                   "The number of days before login passwords expire.  The minimum
                   value is 1 day and the maximum value is 365 days.  The default
                   value is 90 days.  A value of 0 disables this option."
                   ::= { customSecuritySettings 2 }

           minimumPasswordReuseCycle OBJECT-TYPE
                   SYNTAX  INTEGER {
                     none(0),
                     onePassword(1),
                     twoPasswords(2),
                     threePasswords(3),
                     fourPasswords(4),
                     fivePasswords(5)
                   }
                   ACCESS  read-write
                   STATUS  mandatory
                   DESCRIPTION
                   "The number of unique passwords a user must choose before
                   reusing a password.  The default value is none."
                   ::= { customSecuritySettings 3 }


       getPwdLeftDaysTable  OBJECT-TYPE
                            SYNTAX SEQUENCE OF PwdLeftDaysEntry
                            ACCESS  not-accessible
                            STATUS  mandatory
                            DESCRIPTION
                            "Get left days before password expired table."
                              ::= { generalRemoteCfg 13 }

       getPwdLeftDaysEntry  OBJECT-TYPE
                            SYNTAX PwdLeftDaysEntry
                            ACCESS  not-accessible
                            STATUS  mandatory
                            DESCRIPTION
                            "Get left days before password expired entry."
                            INDEX { userLeftPwdDaysIndex }
                              ::= { getPwdLeftDaysTable 1 }


      PwdLeftDaysEntry ::= SEQUENCE {
                   userLeftPwdDaysIndex INTEGER(0..255),
                   userPwdLeftDaysValue INTEGER(0..365)
      }

      userLeftPwdDaysIndex  OBJECT-TYPE
                    SYNTAX  INTEGER(0..255)
                    ACCESS  read-only
                    STATUS  mandatory
                    DESCRIPTION
                    "Index for User ."
                    ::= { getPwdLeftDaysEntry 1 }

      userPwdLeftDaysValue    OBJECT-TYPE
                    SYNTAX  INTEGER(0..365)
                    ACCESS  read-only
                    STATUS  mandatory
                    DESCRIPTION
                    "left days before password expired for selected user"
                    ::= { getPwdLeftDaysEntry 2 }
    -- ***********************************************************************
    -- ASM Serial Port Configuration
    -- ***********************************************************************
     serialPortCfg  OBJECT IDENTIFIER ::= { remoteAccessConfig 2 }

      -- ***********************************************************************
      -- Serial Port  1  Configuration
      -- ***********************************************************************
      serialPort1Cfg OBJECT IDENTIFIER ::= { serialPortCfg 1 }

       port1Baud    OBJECT-TYPE
                    SYNTAX  INTEGER {
                      baud2400(0),
                      baud4800(1),
                      baud9600(3),
                      baud19200(7),
                      baud38400(15),
                      baud57600(23)
                    }
                    ACCESS  read-write
                    STATUS  mandatory
                    DESCRIPTION
                    "Baud rate for ASM serial port 1.

                    Note: ASM on some servers does not have serial port support."
                    ::= { serialPort1Cfg 1 }

       port1Parity  OBJECT-TYPE
                    SYNTAX  INTEGER {
                      none(0),
                      odd(1),
                      even(3),
                      mark(5),
                      space(7)
                    }
                    ACCESS  read-write
                    STATUS  mandatory
                    DESCRIPTION
                    "Parity setting ASM for serial port 1.

                    Note: ASM on some servers does not have serial port support."
                    ::= { serialPort1Cfg 2 }

       port1StopBits OBJECT-TYPE
                    SYNTAX  INTEGER {
                      oneStopbit(0),
                      twoOrOnePtFive(1)
                    }
                    ACCESS  read-write
                    STATUS  mandatory
                    DESCRIPTION
                    "Number of stop bits for ASM serial port 1.

                    Note: ASM on some servers does not have serial port support."
                    ::= { serialPort1Cfg 3 }

       port1ModemInitString OBJECT-TYPE
                    SYNTAX  OCTET STRING (SIZE(0..128))
                    ACCESS  read-write
                    STATUS  mandatory
                    DESCRIPTION
                    "Null terminated modem initialization string for ASM serial port 1.
                    The string must contain a '^M' that will represent a carriage
                    return character in the string, for example 'ATZ^M'.

                    Note: ASM on some servers does not have serial port support."
                    ::= { serialPort1Cfg 5 }

       port1ModemCallerIdString OBJECT-TYPE
                    SYNTAX  OCTET STRING (SIZE(0..32))
                    ACCESS  read-write
                    STATUS  mandatory
                    DESCRIPTION
                    "Null terminated caller ID for ASM serial port 1 string to obtain caller
                    ID information from the modem.

                    Note: ASM on some servers does not have serial port support."
                    ::= { serialPort1Cfg 7}

       port1ModemFactorySetString  OBJECT-TYPE
                    SYNTAX  OCTET STRING (SIZE(0..16))
                    ACCESS  read-write
                    STATUS  mandatory
                    DESCRIPTION
                    "Null terminated modem return to factory settings string for ASM serial port 1.
                    The string must contain a '^M' that will represent a carriage
                    return character in the string, for example 'AT&F0^M'.

                    Note: ASM on some servers does not have serial port support."
                    ::= { serialPort1Cfg 8 }

       port1ModemEscapeTime  OBJECT-TYPE
                    SYNTAX  INTEGER
                    ACCESS  read-write
                    STATUS  mandatory
                    DESCRIPTION
                    "Length of time to wait after the escape string is issued to
                    the modem in .01 second intervals for ASM serial port 1.
                    For example a value of 100 will be 1 second.

                    Note: ASM on some servers does not have serial port support."
                    ::= { serialPort1Cfg 9 }

       port1ModemEscapeString OBJECT-TYPE
                    SYNTAX  OCTET STRING (SIZE(0..16))
                    ACCESS  read-write
                    STATUS  mandatory
                    DESCRIPTION
                    "Null terminated escape string to return modem to command mode,
                    for example '+++' for ASM serial port 1.

                    Note: ASM on some servers does not have serial port support."
                    ::= { serialPort1Cfg 10 }

       port1ModemDialPrefixString OBJECT-TYPE
                    SYNTAX  OCTET STRING (SIZE(0..16))
                    ACCESS  read-write
                    STATUS  mandatory
                    DESCRIPTION
                    "Null terminated modem dial prefix string for ASM serial port 1,
                    placed before the number that dials the remote modem, for example ATDT.

                    Note: ASM on some servers does not have serial port support."
                    ::= { serialPort1Cfg 11 }

       port1ModemDialPostfixString OBJECT-TYPE
                    SYNTAX  OCTET STRING (SIZE(0..16))
                    ACCESS  read-write
                    STATUS  mandatory
                    DESCRIPTION
                    "Null terminated modem dial postfix string for ASM serial port 1.
                    The string must contain a '^M' that will represent a carriage
                    return character in the string, for example '^M'.

                    Note: ASM on some servers does not have serial port support."
                    ::= { serialPort1Cfg 12 }

       port1ModemAutoAnswerString OBJECT-TYPE
                    SYNTAX  OCTET STRING (SIZE(0..16))
                    ACCESS  read-write
                    STATUS  mandatory
                    DESCRIPTION
                    "Null terminated modem auto answer string for ASM serial port 1.
                    The string must contain a '^M' that will represent a carriage
                    return character in the string, for example 'ATS0=1^M'.

                    Note: ASM on some servers does not have serial port support."
                    ::= { serialPort1Cfg 13 }

       port1ModemAutoAnswerStopString OBJECT-TYPE
                    SYNTAX  OCTET STRING (SIZE(0..16))
                    ACCESS  read-write
                    STATUS  mandatory
                    DESCRIPTION
                    "Null terminated modem auto answer stop string for ASM serial port 1.
                    The string must contain a '^M' that will represent a carriage
                    return character in the string, for example 'ATS0=0^M'.

                    Note: ASM on some servers does not have serial port support."
                    ::= { serialPort1Cfg 14 }

       port1ModemQueryString  OBJECT-TYPE
                    SYNTAX  OCTET STRING (SIZE(0..16))
                    ACCESS  read-write
                    STATUS  mandatory
                    DESCRIPTION
                    "Null terminated modem query string string for ASM serial port 1.
                    The string must contain a '^M' that will represent a carriage
                    return character in the string, for example 'AT^M'.

                    Note: ASM on some servers does not have serial port support."
                    ::= { serialPort1Cfg 15 }

       port1ModemHangUpString OBJECT-TYPE
                    SYNTAX  OCTET STRING (SIZE(0..16))
                    ACCESS  read-write
                    STATUS  mandatory
                    DESCRIPTION
                    "Null terminated modem hang up string for ASM serial port 1.
                    The string must contain a '^M' that will represent a carriage
                    return character in the string, for example 'ATH0^M'.

                    Note: ASM on some servers does not have serial port support."
                    ::= { serialPort1Cfg 16 }

       port1Function OBJECT-TYPE
                    SYNTAX  INTEGER {
                      modemAlerting(0),
                      serialRedirect(1)
                      -- ppp(2)
                    }
                    ACCESS  read-write
                    STATUS  mandatory
                    DESCRIPTION
                    "Use this field to select the function this serial port will be used for. On ASMs
                    which support PPP over a serial port, selecting 'serialRedirect' as the port
                    function enables the PPP interface for that serial port if the PPP interface has
                    been enabled. Any other selection disables the PPP interface.
                    The functions listed in the pulldown field are mutually exclusive.

                    Note: ASM on some servers does not have serial port support."
                    ::= { serialPort1Cfg 17 }

       port1CLImode OBJECT-TYPE
                    SYNTAX  INTEGER {
                      cliDisable(0),
                      cliWithCMScompatibleKeystrokeSeq(1),
                      cliWithUserDefinedKeystrokeSeq(2)
                    }
                    ACCESS  read-write
                    STATUS  mandatory
                    DESCRIPTION
                    "Use this field to select the CLI (command line interface) mode for this port.
                    The CLI mode specifies the type of keystroke sequences to use for entering/exiting
                    the CLI. The port must be enabled for serial redirection for the CLI to be active
                    and for this setting to have a meaning.

                    Note: ASM on some servers does not have serial port support."
                    ::= { serialPort1Cfg 18 }

       port1CLIauth OBJECT-TYPE
                    SYNTAX  INTEGER {
                      enabled(0),
                      disabled(1)
                    }
                    ACCESS  read-write
                    STATUS  mandatory
                    DESCRIPTION
                    "Use this field to specify whether to skip serial port authentication when
                    the user invokes the CLI from this port. The port must be enabled with CLI
                    active for this setting to have meaning. When set to 'disabled', users can
                    access the CLI without having to authenticate.

                    Note: ASM on some servers does not have serial port support."
                    ::= { serialPort1Cfg 19 }

      -- ***********************************************************************
      -- Serial Port  2  Configuration
      -- ***********************************************************************
      serialPort2Cfg OBJECT IDENTIFIER ::= { serialPortCfg 2 }

       port2Baud    OBJECT-TYPE
                    SYNTAX  INTEGER {
                      baud2400(0),
                      baud4800(1),
                      baud9600(3),
                      baud19200(7),
                      baud38400(15),
                      baud57600(23)
                    }
                    ACCESS  read-write
                    STATUS  mandatory
                    DESCRIPTION
                    "Baud rate for ASM serial port 2.

                    Note: ASM on some servers does not have serial port support."
                    ::= { serialPort2Cfg 1 }

       port2Parity  OBJECT-TYPE
                    SYNTAX  INTEGER {
                      none(0),
                      odd(1),
                      even(3),
                      mark(5),
                      space(7)
                    }
                    ACCESS  read-write
                    STATUS  mandatory
                    DESCRIPTION
                    "Parity setting ASM for serial port 2.

                    Note: ASM on some servers does not have serial port support."
                    ::= { serialPort2Cfg 2 }

       port2StopBits OBJECT-TYPE
                    SYNTAX  INTEGER {
                      oneStopbit(0),
                      twoOrOnePtFive(1)
                    }
                    ACCESS  read-write
                    STATUS  mandatory
                    DESCRIPTION
                    "Number of stop bits for ASM serial port 2.

                    Note: ASM on some servers does not have serial port support."
                    ::= { serialPort2Cfg 3 }

       port2Function OBJECT-TYPE
                    SYNTAX  INTEGER {
                      none(0),
                      serialRedirect(1)
                    }
                    ACCESS  read-write
                    STATUS  mandatory
                    DESCRIPTION
                    "Use this field to select the function this serial port will be used for. On ASMs
                    which support PPP over a serial port, selecting 'PPP' as the port function enables
                    the PPP interface for that port. Any other selection disables the PPP interface.
                    The functions listed in the pulldown field are mutually exclusive.

                    Note: ASM on some servers does not have serial port support."
                    ::= { serialPort2Cfg 4 }

       port2CLImode OBJECT-TYPE
                    SYNTAX  INTEGER {
                      cliDisable(0),
                      cliWithEMScompatibleKeystrokeSeq(1),
                      cliWithUserDefinedKeystrokeSeq(2)
                    }
                    ACCESS  read-write
                    STATUS  mandatory
                    DESCRIPTION
                    "Use this field to select the CLI (command line interface) mode for this port.
                    The CLI mode specifies the type of keystroke sequences to use for entering/exiting
                    the CLI. The port must be enabled for serial redirection for the CLI to be active
                    and for this setting to have a meaning.

                    Note: ASM on some servers does not have serial port support."
                    ::= { serialPort2Cfg 5 }

       port2CLIauth OBJECT-TYPE
                    SYNTAX  INTEGER {
                      enabled(0),
                      disabled(1)
                    }
                    ACCESS  read-write
                    STATUS  mandatory
                    DESCRIPTION
                    "Use this field to specify whether to skip serial port authentication when
                    the user invokes the CLI from this port. The port must be enabled with CLI
                    active for this setting to have meaning. When set to 'disabled', users can
                    access the CLI without having to authenticate.

                    Note: ASM on some servers does not have serial port support."
                    ::= { serialPort2Cfg 6 }


      -- ***********************************************************************
      -- Serial Redirect
      -- ***********************************************************************
      serialRedirect OBJECT IDENTIFIER ::= { serialPortCfg 3 }

       serialPassthru    OBJECT-TYPE
                    SYNTAX  INTEGER {
                      disabled(0),
                      enabled(1)
                    }
                    ACCESS  read-write
                    STATUS  mandatory
                    DESCRIPTION
                    "Use this field to specify whether the two serial ports should be linked for
                    serial redirect. This field is only applicable when the ASM has two serial
                    ports and supports serial redirect. When enabled, if both serial ports are
                    active for serial redirection, the serial ports will automatically be linked
                    so that the input from port 1 is sent to the output of port 2 and the input
                    of port 2 is sent to the output of port 1.

                    Note: ASM on some servers does not have serial port support."
                    ::= { serialRedirect 1 }

      enterCLIkeySeq  OBJECT-TYPE
                      SYNTAX  OCTET STRING(SIZE(0..16))
                      ACCESS  read-write
                      STATUS  mandatory
                      DESCRIPTION
                      "This is the keystroke sequence used to enter the CLI from a serial or telnet
                      port. This sequence must have at least one character. The caret symbol (^)
                      has a special meaning in this sequence. It denotes 'Ctrl' for keystrokes that
                      map to Ctrl sequences (for example, ^[ for the escape key and ^M for carriage
                      return). All ocurrences of ^ will be interpreted as part of a Ctrl sequence.
                      Refer to an ASCII-to-key conversion table for a complete list of Ctrl sequences.
                      The default value for this field is '^[(' i.e. ESC followed by (.

                      Note: ASM on some servers does not have serial port support."
                      ::= { serialRedirect 2 }

      exitCLIkeySeq  OBJECT-TYPE
                     SYNTAX  OCTET STRING(SIZE(0..16))
                     ACCESS  read-write
                     STATUS  mandatory
                     DESCRIPTION
                     "This is the keystroke sequence used to exit the CLI. The same restrictions as
                     the 'Enter CLI' sequence apply to this field. The sequence is not active for
                     the telnet interface, since either COM port may be available from the CLI session
                     for serial redirect (i.e. the meaning is ambiguous). The default value for this
                     field is '^[Q\' i.e. ESC followed by Q.

                      Note: ASM on some servers does not have serial port support."
                     ::= { serialRedirect 3 }

     -- ***********************************************************************
     -- Remote Alert Profiles
     -- ***********************************************************************
     remoteAlertIds OBJECT IDENTIFIER ::= { remoteAccessConfig 3 }


      remoteAlertIdsTable  OBJECT-TYPE
                            SYNTAX  SEQUENCE OF RemoteAlertIdsEntry
                            ACCESS  not-accessible
                            STATUS  mandatory
                            DESCRIPTION
                            "Table of remote alert entries.
                            This table lets you configure remote alert recipients.
                            You can define up to 12 unique recipients.
                            Note: All selected alert events will be sent to all
                            enabled alert recipients."
                            ::= {  remoteAlertIds 1 }

      remoteAlertIdsEntry  OBJECT-TYPE
                            SYNTAX RemoteAlertIdsEntry
                            ACCESS  not-accessible
                            STATUS  mandatory
                            DESCRIPTION
                            "Remote alert entries."
                            INDEX { remoteAlertIdEntryIndex }
                            ::= { remoteAlertIdsTable 1 }


      RemoteAlertIdsEntry ::= SEQUENCE {
                   remoteAlertIdEntryIndex INTEGER,
                   remoteAlertIdEntryStatus INTEGER,
                   remoteAlertIdEntryPhoneNumberOrIP OCTET STRING (SIZE(0..50)),
                   remoteAlertIdEntryTextDescription OCTET STRING (SIZE(0..32)),
                   remoteAlertIdEntryNotificationType INTEGER,
                   remoteAlertIdTxtPagerPinNum OCTET STRING (SIZE(0..16)),
                   remoteAlertIdEmailAddr OCTET STRING (SIZE(0..64)),
                   remoteAlertIdPPPUserId OCTET STRING (SIZE(0..64)),
                   remoteAlertIdPPPPassword OCTET STRING (SIZE(0..16)),
                   remoteAlertIdEntrySelectiveAlert INTEGER
      }


      remoteAlertIdEntryIndex  OBJECT-TYPE
                                SYNTAX  INTEGER
                                ACCESS  read-only
                                STATUS  mandatory
                                DESCRIPTION
                                "Index for remote alert entry."
                                ::= { remoteAlertIdsEntry 1 }

      remoteAlertIdEntryStatus OBJECT-TYPE
                                SYNTAX  INTEGER {
                                  invalid(0),
                                  disabledAndValid(1),
                                  enabledAndValid(2)
                                }
                                ACCESS  read-write
                                STATUS  mandatory
                                DESCRIPTION
                                "Remote alert entry status, invalid means entry
                                not defined yet, disabledAndValid means entry defined
                                but not enabled to send a alert, enabledAndValid means
                                entry defined and enabled to send a alert."
                                ::= { remoteAlertIdsEntry 2 }

      remoteAlertIdEntryPhoneNumberOrIP OBJECT-TYPE
                                   SYNTAX  OCTET STRING (SIZE(0..50))
                                   ACCESS  read-write
                                   STATUS  mandatory
                                   DESCRIPTION
                                   "A null terminated string that either
                                   contains a phone number, a IP address of the form
                                   '1.2.3.4' or a host name(if DNS is enabled) for the
                                   alert entry. Based on the notification method the correct
                                   string must be used.

                                   Note: ASM on some servers does not have serial port
                                   and PPP interface support."
                                   ::= { remoteAlertIdsEntry 3 }

      remoteAlertIdEntryTextDescription  OBJECT-TYPE
                                  SYNTAX  OCTET STRING (SIZE(0..50))
                                  ACCESS  read-write
                                  STATUS  mandatory
                                  DESCRIPTION
                                  "A null terminated string that contains
                                  a text description of this entry."
                                  ::= { remoteAlertIdsEntry 4 }

      remoteAlertIdEntryNotificationType OBJECT-TYPE
                                   SYNTAX  INTEGER {
                                     numPager(0),
                                     alphaNumPager(1),
                                     ibmDirectorOverModem(2),
                                     ibmDirectorOverLAN(3),
                                     snmpOverLan(4),
                                     emailOverLan(5),
                                     snmpOverPPP(6),
                                     emailOverPPP(7),
                                     ibmDirectorComprehensive(8)
                                   }
                                   ACCESS  read-write
                                   STATUS  mandatory
                                   DESCRIPTION
                                   "Remote alert entry notification method. Types include
                                   numPager for a numeric pager alert, alphaNumPager
                                   for a alphanumeric pager alert, ibmDirectorOverModem
                                   for a modem alert to IBM director, ibmDirectorOverLAN
                                   for a LAN alert sent over ethernet to IBM director,
                                   snmpOverLan for a SNMP alert over ethernet, emailOverLan
                                   for a E-Mail alert over ethernet, snmpOverPPP for a
                                   SNMP alert over a PPP serial connection, emailOverPPP
                                   for a E-mail alert over a PPP serial connection.

                                   Note: ASM on some servers does not have serial port
                                   and PPP interface support."
                                   ::= { remoteAlertIdsEntry 5 }

      remoteAlertIdTxtPagerPinNum  OBJECT-TYPE
                                  SYNTAX  OCTET STRING(SIZE(0..16))
                                  ACCESS  read-write
                                  STATUS  mandatory
                                  DESCRIPTION
                                  "A null terminated string that
                                  contains a Personal Identification Number(PIN).
                                  Used only for a alpha numeric pager notification type.

                                  Note: ASM on some servers does not have serial port
                                  and PPP interface support."
                                  ::= { remoteAlertIdsEntry 8 }

      remoteAlertIdEmailAddr     OBJECT-TYPE
                                  SYNTAX  OCTET STRING(SIZE(0..64))
                                  ACCESS  read-write
                                  STATUS  mandatory
                                  DESCRIPTION
                                  "A null terminated string that
                                  contains a E-Mail Address. For example 'jeb@us.ibm.com'.
                                  Used only for a E-mail over Lan or E-Mail over PPP
                                  notification type.

                                  Note: ASM on some servers does not have serial port
                                  and PPP interface support."
                                  ::= { remoteAlertIdsEntry 9 }

      remoteAlertIdPPPUserId     OBJECT-TYPE
                                  SYNTAX  OCTET STRING(SIZE(0..64))
                                  ACCESS  read-write
                                  STATUS  mandatory
                                  DESCRIPTION
                                  "A null terminated string that
                                  contains a userid for the ISP account. This is needed
                                  for SNMP and E-mail PPP alert notification
                                  types. For example for the IBM Global Network
                                  the format is 'service.account.userid'. Where service
                                  is 'Secureip' and account.userid is 'NEREG.joe'. This
                                  means the string would be set to 'Secureip.NEREG.joe'.

                                  Note: ASM on some servers does not have serial port
                                  and PPP interface support."
                                  ::= { remoteAlertIdsEntry 10 }

      remoteAlertIdPPPPassword   OBJECT-TYPE
                                  SYNTAX  OCTET STRING(SIZE(0..16))
                                  ACCESS  read-write
                                  STATUS  mandatory
                                  DESCRIPTION
                                  "A null terminated string that
                                  contains a password for the ISP account. This is needed
                                  for SNMP and E-mail PPP alert notification
                                  types.

                                  Note: ASM on some servers does not have serial port
                                  and PPP interface support."
                                  ::= { remoteAlertIdsEntry 11 }

      remoteAlertIdEntrySelectiveAlert OBJECT-TYPE
                                  SYNTAX  INTEGER {
                                    critOnlyAlerts(0),
                                    allAlerts(1)
                                  }
                                  ACCESS  read-write
                                  STATUS  mandatory
                                  DESCRIPTION
                                  "Remote alert entry selective alert setting. A value of
                                  critOnlyAlerts will only send critical alerts to this
                                  remote alert receipient, a value of allAlerts
                                  will send all alerts to this remote alert recepient."
                                  ::= { remoteAlertIdsEntry 13 }

      generateTestAlert  OBJECT-TYPE
                   SYNTAX  INTEGER {
                    execute(1)
                   }
                   ACCESS  write-only
                   STATUS  mandatory
                   DESCRIPTION
                   "Generate a Test Alert. This will send a test alert to all configured
                   and enabled remote alert receipients. The text portion of the
                   alert will contain 'Application Posted Alert to ASM'."
                   ::= { remoteAlertIds 30 }

     -- ***********************************************************************
     -- Remote Access Profiles
     -- ***********************************************************************
     remoteAccessIds OBJECT IDENTIFIER ::= { remoteAccessConfig 4 }


      remoteAccessIdsTable  OBJECT-TYPE
                            SYNTAX  SEQUENCE OF RemoteAccessIdsEntry
                            ACCESS  not-accessible
                            STATUS  mandatory
                            DESCRIPTION
                            "Table of remote access profiles.

                            This table lets you to configure all login profiles.
                            You can define up to 12 unique profiles.

                            Note: By default, the remote supervisor adapter
                            comes configured with one login profile that allows remote
                            access using a login ID of 'USERID' and a password of 'PASSW0RD'
                            (the 0 is a zero). To avoid a potential security exposure,
                            we strongly recommend that you change this default Login
                            Profile to values of your choice."
                            ::= {  remoteAccessIds 1 }

      remoteAccessIdsEntry  OBJECT-TYPE
                            SYNTAX RemoteAccessIdsEntry
                            ACCESS  not-accessible
                            STATUS  mandatory
                            DESCRIPTION
                            "Remote access entries."
                            INDEX { remoteAccessIdEntryIndex }
                            ::= { remoteAccessIdsTable 1 }


      RemoteAccessIdsEntry ::= SEQUENCE {
                   remoteAccessIdEntryIndex INTEGER(0..255),
                   remoteAccessIdEntryUserId OCTET STRING (SIZE(0..16)),
                   remoteAccessIdEntryPassword OCTET STRING (SIZE(0..16)),
                   remoteAccessIdEntryDialBackPhoneNum OCTET STRING (SIZE(0..40))
      }


      remoteAccessIdEntryIndex  OBJECT-TYPE
                                SYNTAX  INTEGER(0..255)
                                ACCESS  read-only
                                STATUS  mandatory
                                DESCRIPTION
                                "Index for Remote access entry."
                                ::= { remoteAccessIdsEntry 1 }

      remoteAccessIdEntryUserId    OBJECT-TYPE
                                SYNTAX  OCTET STRING (SIZE(0..16))
                                ACCESS  read-write
                                STATUS  mandatory
                                DESCRIPTION
                                "Remote access entry null terminated string that
                                contains the user-id."
                                ::= { remoteAccessIdsEntry 2 }

      remoteAccessIdEntryPassword OBJECT-TYPE
                                  SYNTAX  OCTET STRING (SIZE(0..16))
                                  ACCESS  read-write
                                  STATUS  mandatory
                                  DESCRIPTION
                                  "Remote access entry null terminated string that
                                  contains the password. On a read a NULL string
                                  will be returned for security reasons."
                                  ::= { remoteAccessIdsEntry 3 }

      remoteAccessIdEntryDialBackPhoneNum OBJECT-TYPE
                                      SYNTAX  OCTET STRING (SIZE(0..40))
                                      ACCESS  read-write
                                      STATUS  mandatory
                                      DESCRIPTION
                                      "Remote access entry null terminated string that
                                      contains a phone number to be used when accessing
                                      through a modem and for security reasons a dial
                                      back to the caller must be made to establish the
                                      connection."
                                      ::= { remoteAccessIdsEntry 6 }

      -- 51.1.4.1.4.2
      remoteAccessUserAuthorityLevelTable  OBJECT-TYPE
                            SYNTAX  SEQUENCE OF RemoteAccessUserAuthorityLevelEntry
                            ACCESS  not-accessible
                            STATUS  mandatory
                            DESCRIPTION
                            "Table of user authority level profiles."
                            ::= {  remoteAccessIds 2 }

      remoteAccessUserAuthorityLevelEntry  OBJECT-TYPE
                            SYNTAX RemoteAccessUserAuthorityLevelEntry
                            ACCESS  not-accessible
                            STATUS  mandatory
                            DESCRIPTION
                            "User authority level entries."
                            INDEX { ualIndex }
                            ::= { remoteAccessUserAuthorityLevelTable 1 }

      RemoteAccessUserAuthorityLevelEntry ::= SEQUENCE {
                   ualIndex INTEGER(0..255),
                   ualId OCTET STRING (SIZE(0..16)),
                   ualSupervisor INTEGER,
                   ualReadOnly INTEGER,
                   ualAccountManagement INTEGER,
                   ualConsoleAccess INTEGER,
                   ualConsoleAndVirtualMediaAccess INTEGER,
                   ualServerPowerAccess INTEGER,
                   ualAllowClearLog INTEGER,
                   ualAdapterBasicConfig INTEGER,
                   ualAdapterNetworkAndSecurityConfig INTEGER,
                   ualAdapterAdvancedConfig INTEGER
      }

      ualIndex  OBJECT-TYPE
                    SYNTAX  INTEGER(0..255)
                    ACCESS  read-only
                    STATUS  mandatory
                    DESCRIPTION
                    "Index for User Authority Level entry."
                    ::= { remoteAccessUserAuthorityLevelEntry 1 }

      ualId    OBJECT-TYPE
                    SYNTAX  OCTET STRING (SIZE(0..16))
                    ACCESS  read-only
                    STATUS  mandatory
                    DESCRIPTION
                    "User ID"
                    ::= { remoteAccessUserAuthorityLevelEntry 2 }

      ualSupervisor OBJECT-TYPE
                    SYNTAX  INTEGER {
                       disabled(0),
                       enabled(1)
                    }
                    ACCESS  read-write
                    STATUS  mandatory
                    DESCRIPTION
                    "User has no restrictions."
                    ::= { remoteAccessUserAuthorityLevelEntry 3 }

      ualReadOnly OBJECT-TYPE
                    SYNTAX  INTEGER {
                       disabled(0),
                       enabled(1)
                    }
                    ACCESS  read-write
                    STATUS  mandatory
                    DESCRIPTION
                    "User has only read-only access, and cannot perform any save, modify,
                    clear, or state affecting operations (eg. restart ASM, restore defaults,
                    upgrade the firmware, etc.)."
                    ::= { remoteAccessUserAuthorityLevelEntry 4 }

      ualAccountManagement OBJECT-TYPE
                    SYNTAX  INTEGER {
                       disabled(0),
                       enabled(1)
                    }
                    ACCESS  read-write
                    STATUS  mandatory
                    DESCRIPTION
                    "User can add/modify/delete users and change the global login settings in
                    the Login Profiles panel."
                    ::= { remoteAccessUserAuthorityLevelEntry 5 }

      ualConsoleAccess OBJECT-TYPE
                    SYNTAX  INTEGER {
                       disabled(0),
                       enabled(1)
                    }
                    ACCESS  read-write
                    STATUS  mandatory
                    DESCRIPTION
                    "User can access the remote console."
                    ::= { remoteAccessUserAuthorityLevelEntry 6 }

      ualConsoleAndVirtualMediaAccess OBJECT-TYPE
                    SYNTAX  INTEGER {
                       disabled(0),
                       enabled(1)
                    }
                    ACCESS  read-write
                    STATUS  mandatory
                    DESCRIPTION
                    "User can access both the remote console and the virtual media feature."
                    ::= { remoteAccessUserAuthorityLevelEntry 7 }

      ualServerPowerAccess OBJECT-TYPE
                    SYNTAX  INTEGER {
                       disabled(0),
                       enabled(1)
                    }
                    ACCESS  read-write
                    STATUS  mandatory
                    DESCRIPTION
                    "User can access the power on and restart functions for the remote server.
                    These functions are available via the Power/Restart panel."
                    ::= { remoteAccessUserAuthorityLevelEntry 8 }

      ualAllowClearLog OBJECT-TYPE
                    SYNTAX  INTEGER {
                       disabled(0),
                       enabled(1)
                    }
                    ACCESS  read-write
                    STATUS  mandatory
                    DESCRIPTION
                    "User can clear the event logs. Everyone can look at the
                    event logs, but this particular permission is required to clear the logs."
                    ::= { remoteAccessUserAuthorityLevelEntry 9 }

      ualAdapterBasicConfig OBJECT-TYPE
                    SYNTAX  INTEGER {
                       disabled(0),
                       enabled(1)
                    }
                    ACCESS  read-write
                    STATUS  mandatory
                    DESCRIPTION
                    "User can modify configuration parameters in the System Settings and Alerts
                    panels."
                    ::= { remoteAccessUserAuthorityLevelEntry 10 }

      ualAdapterNetworkAndSecurityConfig OBJECT-TYPE
                    SYNTAX  INTEGER {
                       disabled(0),
                       enabled(1)
                    }
                    ACCESS  read-write
                    STATUS  mandatory
                    DESCRIPTION
                    "User can modify configuration parameters in the Security, Network Protocols,
                    Network Interface, Port Assignments, and Serial Port panels."
                    ::= { remoteAccessUserAuthorityLevelEntry 11 }

      ualAdapterAdvancedConfig OBJECT-TYPE
                    SYNTAX  INTEGER {
                       disabled(0),
                       enabled(1)
                    }
                    ACCESS  read-write
                    STATUS  mandatory
                    DESCRIPTION
                    "User has no restrictions when configuring the adapter. In addition, the
                    user is said to have administrative access to the RSA, meaning that the
                    user can also perform the following advanced functions: firmware upgrades,
                    PXE network boot, restore adapter factory defaults, modify and restore
                    adapter configuration from a configuration file, and restart/reset the
                    adapter."
                    ::= { remoteAccessUserAuthorityLevelEntry 12 }


     -- ***********************************************************************
    -- Remote Alert Error types
    -- ***********************************************************************
    remoteAlertErrors  OBJECT IDENTIFIER ::= { configureSP 2 }

     -- ***********************************************************************
     -- Remote Alert Critical Error types
     -- ***********************************************************************
     remoteAlertErrsCrit  OBJECT IDENTIFIER ::= { remoteAlertErrors 1 }

      critTemp     OBJECT-TYPE
                   SYNTAX  INTEGER {
                     disabled(0),
                     enabled(1)
                   }
                   ACCESS  read-write
                   STATUS  mandatory
                   DESCRIPTION
                   "Generate a alert if any of the monitored temperature sensors
                   in the system exceed their critical threshold.

                   Note: If a critical Temperature condition is detected,
                   the server will automatically be shut down and powered off
                   whether this object is enabled or not."
                   ::= { remoteAlertErrsCrit 1 }

      critVoltage  OBJECT-TYPE
                   SYNTAX  INTEGER {
                     disabled(0),
                     enabled(1)
                   }
                   ACCESS  read-write
                   STATUS  mandatory
                   DESCRIPTION
                   "Generate a alert if any of the monitored power supply sensors
                   in the system fall outside their specified critical
                   operational range.

                   Note: If a critical voltage condition is detected,
                   the server will automatically be shut down and powered off
                   whether this object is enabled or not."
                   ::= { remoteAlertErrsCrit 2 }

      critTamper   OBJECT-TYPE
                   SYNTAX  INTEGER {
                     disabled(0),
                     enabled(1)
                   }
                   ACCESS  read-write
                   STATUS  mandatory
                   DESCRIPTION
                   "Generate a alert if physical intrusion of the box is detected
                   This will only happen if the system contains physical intrusion
                   detection hardware."
                   ::= { remoteAlertErrsCrit 3 }

      critMultiFan OBJECT-TYPE
                   SYNTAX  INTEGER {
                     disabled(0),
                     enabled(1)
                   }
                   ACCESS  read-write
                   STATUS  mandatory
                   DESCRIPTION
                   "Generate a alert if mutiple fans used for cooling the system fail."
                   ::= { remoteAlertErrsCrit 4 }

      critPower    OBJECT-TYPE
                   SYNTAX  INTEGER {
                     disabled(0),
                     enabled(1)
                   }
                   ACCESS  read-write
                   STATUS  mandatory
                   DESCRIPTION
                   "Generate a alert if any of the system power supplies fail."
                   ::= { remoteAlertErrsCrit 5 }

      critHardDrv OBJECT-TYPE
                   SYNTAX  INTEGER {
                     disabled(0),
                     enabled(1)
                   }
                   ACCESS  read-write
                   STATUS  mandatory
                   DESCRIPTION
                   "Generate a alert if any of hard disk drives fail."
                   ::= { remoteAlertErrsCrit 6 }

      critVRM     OBJECT-TYPE
                   SYNTAX  INTEGER {
                     disabled(0),
                     enabled(1)
                   }
                   ACCESS  read-write
                   STATUS  mandatory
                   DESCRIPTION
                   "Generate a alert if any of VRM(voltage regulator modules) fail."
                   ::= { remoteAlertErrsCrit 7 }


     -- ***********************************************************************
     -- Remote Alert Warning(non-critical) Error types
     -- ***********************************************************************
     remoteAlertErrsNonCrit  OBJECT IDENTIFIER ::= { remoteAlertErrors 2 }

      warnRedundantPwrSupply OBJECT-TYPE
                    SYNTAX  INTEGER {
                     disabled(0),
                     enabled(1)
                    }
                    ACCESS  read-write
                    STATUS  mandatory
                    DESCRIPTION
                    "Generate a alert if a redundant power supply fails."
                    ::= { remoteAlertErrsNonCrit 1 }

      warnSingleFan OBJECT-TYPE
                    SYNTAX  INTEGER {
                      disabled(0),
                      enabled(1)
                    }
                    ACCESS  read-write
                    STATUS  mandatory
                    DESCRIPTION
                    "Generate a alert if one fan used for cooling the system fails."
                    ::= { remoteAlertErrsNonCrit 2 }

      warnTemp     OBJECT-TYPE
                   SYNTAX  INTEGER {
                     disabled(0),
                     enabled(1)
                   }
                   ACCESS  read-write
                   STATUS  mandatory
                   DESCRIPTION
                   "Generate a alert if any of the monitored temperature sensors
                   in the system exceed their warning threshold."
                   ::= { remoteAlertErrsNonCrit 3 }

      warnVoltage  OBJECT-TYPE
                   SYNTAX  INTEGER {
                     disabled(0),
                     enabled(1)
                   }
                   ACCESS  read-write
                   STATUS  mandatory
                   DESCRIPTION
                   "Generate a alert if any of the monitored power supply sensors
                   in the system fall outside their specified warning
                   operational range."
                   ::= { remoteAlertErrsNonCrit 4 }



     -- ***********************************************************************
     -- Remote Alert System Error types
     -- ***********************************************************************
     remoteAlertErrsSystem  OBJECT IDENTIFIER ::= { remoteAlertErrors 3 }


      systemPOST    OBJECT-TYPE
                    SYNTAX  INTEGER {
                     disabled(0),
                     enabled(1)
                    }
                    ACCESS  read-write
                    STATUS  mandatory
                    DESCRIPTION
                    "Generate a alert if the POST watchdog timeout value has been
                    exceeded."
                    ::= { remoteAlertErrsSystem 1 }

      systemOSHang  OBJECT-TYPE
                    SYNTAX  INTEGER {
                      disabled(0),
                      enabled(1)
                    }
                    ACCESS  read-write
                    STATUS  mandatory
                    DESCRIPTION
                    "Generate a alert if the OS watchdog timeout value has been
                    exceeded."
                    ::= { remoteAlertErrsSystem 2 }

      systemPwrOff OBJECT-TYPE
                   SYNTAX  INTEGER {
                     disabled(0),
                     enabled(1)
                   }
                   ACCESS  read-write
                   STATUS  mandatory
                   DESCRIPTION
                   "Generate a alert if the system is powered off."
                   ::= { remoteAlertErrsSystem 4 }

      systemPwrOn  OBJECT-TYPE
                   SYNTAX  INTEGER {
                     disabled(0),
                     enabled(1)
                   }
                   ACCESS  read-write
                   STATUS  mandatory
                   DESCRIPTION
                   "Generate a alert if the system is powered on."
                   ::= { remoteAlertErrsSystem 5 }

      systemBoot   OBJECT-TYPE
                   SYNTAX  INTEGER {
                     disabled(0),
                     enabled(1)
                   }
                   ACCESS  read-write
                   STATUS  mandatory
                   DESCRIPTION
                   "Generate a alert if the system fails to boot."
                   ::= {  remoteAlertErrsSystem 6 }

      systemLoader OBJECT-TYPE
                   SYNTAX  INTEGER {
                     disabled(0),
                     enabled(1)
                   }
                   ACCESS  read-write
                   STATUS  mandatory
                   DESCRIPTION
                   "Generate a alert if the System Loader watchdog timeout value
                   has been exceeded."
                   ::= {  remoteAlertErrsSystem 7 }

      systemPFA    OBJECT-TYPE
                   SYNTAX  INTEGER {
                     disabled(0),
                     enabled(1)
                   }
                   ACCESS  read-write
                   STATUS  mandatory
                   DESCRIPTION
                   "Generate a alert if the system hardware detects a Predictive
                   Failure Analysis(PFA) on PFA enabled hardware."
                   ::= {  remoteAlertErrsSystem 8 }

      systemPartitionCFG    OBJECT-TYPE
                            SYNTAX  INTEGER {
                              disabled(0),
                              enabled(1)
                            }
                            ACCESS  read-write
                            STATUS  mandatory
                            DESCRIPTION
                            "Generate a alert if the system hardware detects a Partition
                            Configuration."
                            ::= {  remoteAlertErrsSystem 9 }

      systemEventLog        OBJECT-TYPE
                            SYNTAX  INTEGER {
                              disabled(0),
                              enabled(1)
                            }
                            ACCESS  read-write
                            STATUS  mandatory
                            DESCRIPTION
                            "Generate a alert if the event log fills or is cleared."
                            ::= {  remoteAlertErrsSystem 16 }

    -- ***********************************************************************
    -- SP Clock
    -- ***********************************************************************
    spClock        OBJECT IDENTIFIER ::= { configureSP 4 }

     spClockDateAndTimeSetting OBJECT-TYPE
                  SYNTAX  OCTET STRING
                  ACCESS  read-write
                  STATUS  mandatory
                  DESCRIPTION
                  "ASM clock date and time setting.
                  A date-time specification for the local time of day.
                  For example to set the date and time to
                  March 4, 2001 at 06:00:00AM, set the value to:'03/04/2001,06:00:00'.
                  field  contents         range
                  _____  ________         _____
                    1     month           01..12
                    2     separator       '/'
                    3     day             01..31
                    4     separator       '/'
                    5     year            2000..2089
                    6     separator       ','
                    7     hour            00..23
                    8     separator       ':'
                    9     minutes         00..59
                    10    separator       ':'
                    11    seconds         00..59
                  "
                  ::= { spClock  1 }

     spClockTimezoneSetting OBJECT-TYPE
                  SYNTAX  OCTET STRING
                  ACCESS  read-write
                  STATUS  mandatory
                  DESCRIPTION
                  "ASM clock Greenwich Mean Time(GMT) offset and Daylight Saving Time(DST)
                  settings.

                  The following table lists GMT offsets and associated DST
                  information.  DST is not observed in time zones where
                  the 'Observe DST' value does not contain 'yes' in the table.
                  Also, note that in some cases additional information
                  is required to determine the clock adjustment when DST is
                  observed.  The additional information is required when the
                  GMT offset being written is +2:00 or +10:00.

                  Examples
                        -to set the GMT offset to +3:30,
                         set the value to:'+3:30,no'

                        -for Eastern Standard Time and observing DST,
                         set the value to:'-5:00,yes'

                        -for Egypt and observing DST,
                         set the value to:'+2:00,yes,6'


                   GMT    Observe  Additional
                  Offset    DST?    DST value
                  ______  _______  __________
                   +0:00  yes|no
                   +1:00  yes|no
                   +2:00  yes|no   When 'Observe DST?' value is 'yes':
                                   5 (for E.Europe)
                                   4 (for GTB)
                                   6 (for Egypt)
                                   7 (for FLE)
                   +3:00  yes|no
                   +3:30  yes|no
                   +4:00  no
                   +4:30  no
                   +5:00  yes|no
                   +5:30  no
                   +6:00  no
                   +7:00  no
                   +8:00  no
                   +9:00  yes|no
                   +9:30  yes|no
                  +10:00  yes|no   When 'Observe DST?' value is 'yes':
                                   9  (for AUS Eastern)
                                   10 (for Tasmania)
                                   4  (for Vladivostok)
                  +11:00  no
                  +12:00  yes|no   When 'Observe DST?' value is 'yes':
                                   4   (for Kamchatka (Russia))
                                   11  (New Zealand)
                  -12:00  no
                  -11:00  no
                  -10:00  no
                   -9:00  yes|no
                   -8:00  yes|no
                   -7:00  yes|no
                   -6:00  yes|no
                   -5:00  yes|no
                   -4:00  yes|no
                   -3:30  yes|no
                   -3:00  yes|no
                   -2:00  yes|no
                   -1:00  yes|no
                   "
                  ::= { spClock  2 }


    -- ***********************************************************************
    -- SP identification
    -- ***********************************************************************
    spIdentification        OBJECT IDENTIFIER ::= { configureSP 5 }

     spTxtId      OBJECT-TYPE
                  SYNTAX  OCTET STRING (SIZE(0..16))
                  ACCESS  read-write
                  STATUS  mandatory
                  DESCRIPTION
                  "ASM text ID. Note: Do not put any 'space
                  character' at end of the ID."
                  ::= { spIdentification 1 }

     spNumId     OBJECT-TYPE
                   SYNTAX  OCTET STRING (SIZE(0..16))
                   ACCESS  read-write
                   STATUS  mandatory
                   DESCRIPTION
                   "ASM numeric ID."
                   ::= { spIdentification 2 }


    -- ***********************************************************************
    -- Network Configuration
    -- ***********************************************************************
    networkConfiguration  OBJECT IDENTIFIER ::= { configureSP 9 }

     -- ***********************************************************************
     -- Network Interfaces
     -- ***********************************************************************
     networkInterfaces  OBJECT IDENTIFIER ::= { networkConfiguration 1 }
      -- ***********************************************************************
      -- Ethernet Interface 1
      -- ***********************************************************************
      ethernetInterface  OBJECT IDENTIFIER ::= { networkInterfaces 1 }

       ethernetInterfaceType OBJECT-TYPE
                    SYNTAX  OCTET STRING (SIZE(0..16))
                    ACCESS  read-only
                    STATUS  mandatory
                    DESCRIPTION
                    "The type of interface. Indicates 'Ethernet-1'."
                    ::= { ethernetInterface 1 }

       ethernetInterfaceEnabled  OBJECT-TYPE
                    SYNTAX  INTEGER {
                      interfaceDisabled(0),
                      interfaceEnabled(1)
                    }
                    ACCESS  read-write
                    STATUS  mandatory
                    DESCRIPTION
                    "Disable or enable the interface.

                    Note: To alter any of the configuration settings for the ethernet
                    interface the following procedure should be used:
                    (1)This object should be written with 'interfaceDisabled'
                    (2)Make the modifications to other settings
                    (3)This object should be written with 'interfaceEnabled'
                    (4)Restart the remote supervisor adapter

                    Also note that when this object has a value of interfaceEnabled
                    the following is verifed, if this verification fails a error
                    response will be returned for the set of this object and the
                    ethernet interface will be left in a disabled state.
                    (1)Is the range for the MTU between 60-1500
                    (2)Are the speed settings one of 10Mb, 100Mb, AUTO
                    (3)Are the speed settings one of Half, Full, AUTO
                    (4)If DHCP is disabled then is there a valid IP address
                    "
                    ::= { ethernetInterface 2 }

       ethernetInterfaceHostName  OBJECT-TYPE
                    SYNTAX  OCTET STRING (SIZE(0..64))
                    ACCESS  read-write
                    STATUS  mandatory
                    DESCRIPTION
                    "Contains the 64 byte null terminated DNS host name for this
                    interface."
                    ::= { ethernetInterface 3 }

       ethernetInterfaceIPAddress   OBJECT-TYPE
                    SYNTAX  IpAddress
                    ACCESS  read-write
                    STATUS  mandatory
                    DESCRIPTION
                    "Contains the IP address for the ethernet interface."
                    ::= { ethernetInterface 4 }

       ethernetInterfaceDataRate   OBJECT-TYPE
                    SYNTAX  INTEGER {
                      enet10Megabit(3),
                      enet100Megabit(4),
                      autoSpeed(5)
                    }
                    ACCESS  read-write
                    STATUS  mandatory
                    DESCRIPTION
                    "Specifies the data transfer rate to be used over the ethernet
                    interface 10Mb/100Mb/Auto."
                    ::= { ethernetInterface 5 }

       ethernetInterfaceDuplexSetting  OBJECT-TYPE
                    SYNTAX  INTEGER {
                      fullDuplex(1),
                      halfDuplex(2),
                      autoDuplex(3)
                    }
                    ACCESS  read-write
                    STATUS  mandatory
                    DESCRIPTION
                    "Specifies the duplex settings for the data transfer rate to be used over
                    the ethernet interface Half/Full/Auto."
                    ::= { ethernetInterface 6 }

       ethernetInterfaceLAA OBJECT-TYPE
                    SYNTAX  OCTET STRING (SIZE(6))
                    ACCESS  read-write
                    STATUS  mandatory
                    DESCRIPTION
                    "Specifies the locally administered MAC address.  The locally administered
                    address must be a hexadecimal value between 000000000000 - FFFFFFFFFFFF.  This
                    value must be in the form XX:XX:XX:XX:XX:XX where 'X' is a number between 0 - 9 and
                    A - F.  This ASM subsystem does not allow use of a multicast address.  A multicast
                    address has the least significant bit of the first byte set to a 1.  The first
                    byte must, therefore, be an even number."
                    ::= { ethernetInterface 7 }

       ethernetInterfaceDhcpEnabled  OBJECT-TYPE
                    SYNTAX  INTEGER {
                      dhcpDisabled(0),
                      dhcpEnabled(1)
                    }
                    ACCESS  read-write
                    STATUS  mandatory
                    DESCRIPTION
                    "Disable or enable DHCP on this interface."
                    ::= { ethernetInterface 8 }

       ethernetInterfaceGatewayIPAddress   OBJECT-TYPE
                    SYNTAX  IpAddress
                    ACCESS  read-write
                    STATUS  mandatory
                    DESCRIPTION
                    "Contains the IP address of the gateway/router for the ethernet
                     interface."
                    ::= { ethernetInterface 9 }

       ethernetInterfaceBIA OBJECT-TYPE
                    SYNTAX  OCTET STRING (SIZE(6))
                    ACCESS  read-only
                    STATUS  mandatory
                    DESCRIPTION
                    "Specifies the burned-in MAC (BIA) address."
                    ::= { ethernetInterface 10 }

       ethernetInterfaceMTU   OBJECT-TYPE
                    SYNTAX  INTEGER
                    ACCESS  read-write
                    STATUS  mandatory
                    DESCRIPTION
                    "Contains the Maximum Transmission Unit(MTU) for the ethernet
                    interface"
                    ::= { ethernetInterface 13 }

       ethernetInterfaceSubnetMask   OBJECT-TYPE
                    SYNTAX  IpAddress
                    ACCESS  read-write
                    STATUS  mandatory
                    DESCRIPTION
                    "Contains the Subnet Mask for the ethernet
                    interface"
                    ::= { ethernetInterface 14 }

       -- ***********************************************************************
       -- DHCP Server Assigned Settings for ethernet interface 1
       -- ***********************************************************************
       dhcpEthernetInterface  OBJECT IDENTIFIER ::= { ethernetInterface 16 }

        dhcpHostName  OBJECT-TYPE
                     SYNTAX  OCTET STRING (SIZE(0..64))
                     ACCESS  read-only
                     STATUS  mandatory
                     DESCRIPTION
                     "Contains the 64 byte null terminated DNS host name for this
                     interface, assigned by the DHCP server."
                     ::= { dhcpEthernetInterface 1 }

        dhcpIPAddress   OBJECT-TYPE
                     SYNTAX  IpAddress
                     ACCESS  read-only
                     STATUS  mandatory
                     DESCRIPTION
                     "Contains the IP address for the ehternet interface,
                     assigned by the DHCP server."
                     ::= { dhcpEthernetInterface 2 }

        dhcpGatewayIPAddress   OBJECT-TYPE
                     SYNTAX  IpAddress
                     ACCESS  read-only
                     STATUS  mandatory
                     DESCRIPTION
                     "Contains the IP address of the gateway/router for the ethernet
                      interface, assigned by the DHCP server."
                     ::= { dhcpEthernetInterface 3 }

        dhcpSubnetMask   OBJECT-TYPE
                     SYNTAX  IpAddress
                     ACCESS  read-only
                     STATUS  mandatory
                     DESCRIPTION
                     "Contains the Subnet Mask for the ethernet
                     interface, assigned by the DHCP server."
                     ::= { dhcpEthernetInterface 4 }

        dhcpDomainName  OBJECT-TYPE
                     SYNTAX  OCTET STRING (SIZE(0..64))
                     ACCESS  read-only
                     STATUS  mandatory
                     DESCRIPTION
                     "Contains the 64 byte null terminated Domain Name for this
                     interface, assigned by the DHCP server."
                     ::= { dhcpEthernetInterface 5 }

        dhcpDHCPServer  OBJECT-TYPE
                     SYNTAX  IpAddress
                     ACCESS  read-only
                     STATUS  mandatory
                     DESCRIPTION
                     "Contains the DHCP server IP address used to acquire the
                     DHCP settings."
                     ::= { dhcpEthernetInterface 6 }

        dhcpPrimaryDNSServer  OBJECT-TYPE
                     SYNTAX  IpAddress
                     ACCESS  read-only
                     STATUS  mandatory
                     DESCRIPTION
                     "Contains the Primary DNS server, assigned by the DHCP server."
                     ::= { dhcpEthernetInterface 7 }

        dhcpSecondaryDNSServer  OBJECT-TYPE
                     SYNTAX  IpAddress
                     ACCESS  read-only
                     STATUS  mandatory
                     DESCRIPTION
                     "Contains the Secondary DNS server, assigned by the DHCP server."
                     ::= { dhcpEthernetInterface 8 }

        dhcpTertiaryDNSServer  OBJECT-TYPE
                     SYNTAX  IpAddress
                     ACCESS  read-only
                     STATUS  mandatory
                     DESCRIPTION
                     "Contains the tertiary DNS server, assigned by the DHCP server."
                     ::= { dhcpEthernetInterface 9 }
      -- ***********************************************************************
      -- PPP Interface 1
      -- ***********************************************************************
      pppInterface  OBJECT IDENTIFIER ::= { networkInterfaces 2 }

       pppInterfaceType     OBJECT-TYPE
                    SYNTAX  OCTET STRING (SIZE(0..16))
                    ACCESS  read-only
                    STATUS  mandatory
                    DESCRIPTION
                    "The type of interface. Indicates 'PPP-1'.

                    Note: ASM on some servers does not have PPP interface support."
                    ::= { pppInterface 1 }

       pppInterfaceEnabled  OBJECT-TYPE
                    SYNTAX  INTEGER {
                      interfaceDisabled(0),
                      interfaceEnabled(1)
                    }
                    ACCESS  read-write
                    STATUS  mandatory
                    DESCRIPTION
                    "Disable or enable the PPP interface.
                    Note: To alter any of the configuration settings for the PPP
                    interface the following procedure should be used:
                    (1)This object should be written with 'interfaceDisabled'
                    (2)Make the modifications to other settings
                    (3)This object should be written with 'interfaceEnabled'
                    (4)Restart the remote supervisor adapter

                    Also note that when this object has a value of interfaceEnabled
                    that the following is verifed if this verification fails a error
                    response will be returned for the set of this object and the
                    PPP interface will be left in a disabled state.
                    (1)If the local IP address or the remote IP address is 0.0.0.0

                    Note: ASM on some servers does not have PPP interface support."
                    ::= { pppInterface 2 }

       pppInterfaceLocalIPAddress   OBJECT-TYPE
                    SYNTAX  IpAddress
                    ACCESS  read-write
                    STATUS  mandatory
                    DESCRIPTION
                    "Contains the IP address for the ASM side of the PPP link.

                    Note: ASM on some servers does not have PPP interface support."
                    ::= { pppInterface 4 }

       pppInterfaceRemoteIPAddress   OBJECT-TYPE
                    SYNTAX  IpAddress
                    ACCESS  read-write
                    STATUS  mandatory
                    DESCRIPTION
                    "Contains the IP address for the client side of the PPP link.

                    Note: ASM on some servers does not have PPP interface support."
                    ::= { pppInterface 12 }

       pppInterfaceSubnetMask   OBJECT-TYPE
                    SYNTAX  IpAddress
                    ACCESS  read-write
                    STATUS  mandatory
                    DESCRIPTION
                    "Contains the Subnet Mask for the PPP interface.

                    Note: ASM on some servers does not have PPP interface support."
                    ::= { pppInterface 14 }

       pppInterfaceAuthenticationMethod  OBJECT-TYPE
                    SYNTAX  INTEGER {
                      papOnly(1),
                      chapOnly(2),
                      chapThenPap(3)
                    }
                    ACCESS  read-write
                    STATUS  mandatory
                    DESCRIPTION
                    "Authentication method for PPP interface.
                    A value of papOnly indicates Password Authentication Protocol(PAP) will only
                    be allowed for the client trying to dial-in using the PPP interface. This
                    protocol allows the password to be sent in clear text.
                    A value of chapOnly indicates Challenge-Handshake Authentication Protocol(CHAP)
                    will only be allowed for the client trying to dial-in using the PPP
                    interface. This protocol allows the password to be sent encrypted.
                    A value of chaThenPap first atempts CHAP and if does not work then PAP
                    will only be attempted.

                    Note: ASM on some servers does not have PPP interface support."
                    ::= { pppInterface 17 }


     -- ***********************************************************************
     -- TCP/IP Protocol Configuration
     -- ***********************************************************************
     tcpProtocols  OBJECT IDENTIFIER ::= { networkConfiguration 3 }

      -- ***********************************************************************
      -- SNMP Agent Configuration
      -- ***********************************************************************
      snmpAgentConfig  OBJECT IDENTIFIER ::= { tcpProtocols 1 }


       snmpSystemContact     OBJECT-TYPE
                    SYNTAX  OCTET STRING (SIZE(0..48))
                    ACCESS  read-write
                    STATUS  mandatory
                    DESCRIPTION
                    "A NULL terminated 48 byte string that contains the
                    SNMP agent contact name. Note: Set snmpSystemAgentEnable
                    to disabled before performing a set of this object."
                    ::= { snmpAgentConfig 1 }

       snmpSystemLocation     OBJECT-TYPE
                    SYNTAX  OCTET STRING (SIZE(0..48))
                    ACCESS  read-write
                    STATUS  mandatory
                    DESCRIPTION
                    "A NULL terminated 48 byte string that contains the
                    SNMP agent location name. Note: Set snmpSystemAgentEnable
                    to disabled before performing a set of this object."
                    ::= { snmpAgentConfig 2 }

       snmpSystemAgentTrapsDisable  OBJECT-TYPE
                    SYNTAX  INTEGER {
                      trapsEnabled(0),
                      trapsDisabled(1)
                    }
                    ACCESS  read-write
                    STATUS  mandatory
                    DESCRIPTION
                    "Disable or enable SNMP traps. Note: Set snmpSystemAgentEnable
                    to disabled before performing a set of this object."
                    ::= { snmpAgentConfig 3 }

       -- ***********************************************************************
       -- SNMP Agent Community Configuration
       -- ***********************************************************************
       snmpAgentCommunityConfig  OBJECT IDENTIFIER ::= { snmpAgentConfig 4 }


        -- ***********************************************************************
        -- SNMP Community Configuration table
        -- ***********************************************************************

        snmpCommunityTable  OBJECT-TYPE
                              SYNTAX  SEQUENCE OF SnmpCommunityEntry
                              ACCESS  not-accessible
                              STATUS  mandatory
                              DESCRIPTION
                              "Table of SNMP Community entries"
                              ::= {  snmpAgentCommunityConfig 1 }

        snmpCommunityEntry  OBJECT-TYPE
                              SYNTAX  SnmpCommunityEntry
                              ACCESS  not-accessible
                              STATUS  mandatory
                              DESCRIPTION
                              "DASD temperature threshold entries"
                              INDEX { snmpCommunityEntryIndex }
                              ::= { snmpCommunityTable 1 }

        SnmpCommunityEntry ::= SEQUENCE {
                     snmpCommunityEntryIndex INTEGER(0..255),
                     snmpCommunityEntryCommunityName OCTET STRING (SIZE(0..15)),
                     snmpCommunityEntryCommunityIpAddress1 OCTET STRING (SIZE(0..63)),
                     snmpCommunityEntryCommunityIpAddress2 OCTET STRING (SIZE(0..63)),
                     snmpCommunityEntryCommunityIpAddress3 OCTET STRING (SIZE(0..63)),
                     snmpCommunityEntryCommunityViewType INTEGER(1..3)
        }


        snmpCommunityEntryIndex   OBJECT-TYPE
                                  SYNTAX  INTEGER(0..255)
                                  ACCESS  read-only
                                  STATUS  mandatory
                                  DESCRIPTION
                                  "Index for SNMP Agent Community entry."
                                  ::= { snmpCommunityEntry 1 }

        snmpCommunityEntryCommunityName  OBJECT-TYPE
                                  SYNTAX  OCTET STRING (SIZE(0..15))
                                  ACCESS  read-write
                                  STATUS  mandatory
                                  DESCRIPTION
                                  "SNMP Community entry name. Note: Set snmpSystemAgentEnable
                                  to disabled before performing a set of this object."
                                  ::= { snmpCommunityEntry 2 }

        snmpCommunityEntryCommunityIpAddress1  OBJECT-TYPE
                                  SYNTAX  OCTET STRING (SIZE(0..63))
                                  ACCESS  read-write
                                  STATUS  mandatory
                                  DESCRIPTION
                                  "SNMP Community IP address or host name.
                                  Can either be a dotted decimal IP string(eg. 9.37.44.2)
                                  or if DNS is enabled a host name. Note: Set snmpSystemAgentEnable
                                  to disabled before performing a set of this object."
                                  ::= { snmpCommunityEntry 3 }

        snmpCommunityEntryCommunityIpAddress2  OBJECT-TYPE
                                  SYNTAX  OCTET STRING (SIZE(0..63))
                                  ACCESS  read-write
                                  STATUS  mandatory
                                  DESCRIPTION
                                  "SNMP Community IP address or host name.
                                  Can either be a dotted decimal IP string(eg. 9.37.44.2)
                                  or if DNS is enabled a host name.Note: Set snmpSystemAgentEnable
                                  to disabled before performing a set of this object."
                                  ::= { snmpCommunityEntry 4 }

        snmpCommunityEntryCommunityIpAddress3  OBJECT-TYPE
                                  SYNTAX  OCTET STRING (SIZE(0..63))
                                  ACCESS  read-write
                                  STATUS  mandatory
                                  DESCRIPTION
                                  "SNMP Community IP address or host name.
                                  Can either be a dotted decimal IP string(eg. 9.37.44.2)
                                  or if DNS is enabled a host name.Note: Set snmpSystemAgentEnable
                                  to disabled before performing a set of this object."
                                  ::= { snmpCommunityEntry 5 }

                -- 4.9.3.1.4.5
          snmpCommunityEntryCommunityViewType  OBJECT-TYPE
                                     SYNTAX  INTEGER {
                                     read-Traps(1),
                                     write-Read-Traps(2),
                                     traps-Only(3)
                                     }
                                     ACCESS  read-write
                                     STATUS  mandatory
                                     DESCRIPTION
                                     "Access Level of the SNMPv1 managers.  Note this parameter
                                     is set for each community.  Therefore all three managers
                                     in the same community have the same access level."
                                     ::= { snmpCommunityEntry 6 }


       snmpSystemAgentEnable  OBJECT-TYPE
                    SYNTAX  INTEGER {
                      disabled(0),
                      enabled(1)
                    }
                    ACCESS  read-write
                    STATUS  mandatory
                    DESCRIPTION
                    "Disable or enable the SNMP agent.

                    Note: To alter any of the configuration settings for the SNMP Agent
                    the following procedure should be used:
                    (1)This object should be written with 'disabled'
                    (2)Make the modifications to other settings
                    (3)This object should be written with 'enabled'
                    (4)Restart the remote supervisor adapter

                    Also note that when this object has a value of enabled
                    that the following is verifed, if this verification fails a error
                    response will be returned for the set of this object and the SNMP
                    agent will be left in a disabled state.
                    (1)Is there a valid system contact
                    (2)Is there a valid system name
                    (3)Is there at least one valid community name and for that
                    community name is there one valid IP address or hostname
                    "
                    ::= { snmpAgentConfig 5 }

      -- ***********************************************************************
      -- DNS Configuration
      -- ***********************************************************************
      dnsConfig  OBJECT IDENTIFIER ::= { tcpProtocols 2 }

       dnsEnabled   OBJECT-TYPE
                    SYNTAX  INTEGER {
                      dnsDisabled(0),
                      dnsEnabled(1)
                    }
                    ACCESS  read-write
                    STATUS  mandatory
                    DESCRIPTION
                    "Disable or enable the DNS agent.

                    Note: To alter any of the configuration settings for the DNS resolver
                    the following procedure should be used:
                    (1)This object should be written with 'disabled'
                    (2)Make the modifications to other settings
                    (3)This object should be written with 'enabled'
                    (4)Restart the remote supervisor adapter

                    Also note that when this object has a value of enabled
                    that the following is verifed, if this verification fails a error
                    response will be returned for the set of this object and the DNS
                    resolver will be left in a disabled state.
                    (1)Is there at least one valid DNS server IP address
                    "
                    ::= { dnsConfig 1 }

       dnsServerIPAddress1   OBJECT-TYPE
                    SYNTAX  IpAddress
                    ACCESS  read-write
                    STATUS  mandatory
                    DESCRIPTION
                    "Contains the primary DNS server IP address."
                    ::= { dnsConfig 2 }

       dnsServerIPAddress2   OBJECT-TYPE
                    SYNTAX  IpAddress
                    ACCESS  read-write
                    STATUS  mandatory
                    DESCRIPTION
                    "Contains the secondary DNS server IP address."
                    ::= { dnsConfig 3 }

       dnsServerIPAddress3   OBJECT-TYPE
                    SYNTAX  IpAddress
                    ACCESS  read-write
                    STATUS  mandatory
                    DESCRIPTION
                    "Contains the tertiary DNS server IP address."
                    ::= { dnsConfig 4 }



       -- ***********************************************************************
       -- DNS HOST Table Mappings
       -- ***********************************************************************
       dnsHostsIpAddressMapping  OBJECT IDENTIFIER ::= { dnsConfig 5 }


        -- ***********************************************************************
        -- DNS Host table mapping
        -- ***********************************************************************

        dnsHostTable OBJECT-TYPE
                              SYNTAX  SEQUENCE OF DnsHostEntry
                              ACCESS  not-accessible
                              STATUS  mandatory
                              DESCRIPTION
                              "Table of fixed DNS host names to IP address entries.

                              Table ddefines a mapping between an IP address and
                              its corresponding hostname in the event that your
                              network DNS server is unreachable. You can also use
                              these mappings for frequently used host names.

                              Note: The ASM will first look in this table for an
                              address to hostnamemapping. If a match is not found,
                              the data will be requested from the DNS server. If
                              the table contains an entry for a given address, the
                              hostname defined in the table will override any
                              corresponding entry defined on the DNS server.
                              "
                              ::= {  dnsHostsIpAddressMapping 1 }

        dnsHostEntry          OBJECT-TYPE
                              SYNTAX  DnsHostEntry
                              ACCESS  not-accessible
                              STATUS  mandatory
                              DESCRIPTION
                              "DNS host name entry."
                              INDEX { dnsHostEntryIndex }
                              ::= { dnsHostTable 1 }

        DnsHostEntry ::= SEQUENCE {
                     dnsHostEntryIndex INTEGER(0..255),
                     dnsHostEntryHostName OCTET STRING (SIZE(0..63)),
                     dnsHostEntryHostIpAddress IpAddress
        }


        dnsHostEntryIndex         OBJECT-TYPE
                                  SYNTAX  INTEGER(0..255)
                                  ACCESS  read-only
                                  STATUS  mandatory
                                  DESCRIPTION
                                  "Index for DNS Host Table entry."
                                  ::= { dnsHostEntry 1 }

        dnsHostEntryHostName      OBJECT-TYPE
                                  SYNTAX  OCTET STRING (SIZE(0..63))
                                  ACCESS  read-write
                                  STATUS  mandatory
                                  DESCRIPTION
                                  "DNS host table entry host name."
                                  ::= { dnsHostEntry 2 }

        dnsHostEntryHostIpAddress  OBJECT-TYPE
                                  SYNTAX  IpAddress
                                  ACCESS  read-write
                                  STATUS  mandatory
                                  DESCRIPTION
                                  "DNS host table entry host IP Address."
                                  ::= { dnsHostEntry 3 }
      -- ***********************************************************************
      -- SMTP Configuration
      -- ***********************************************************************
      smtpConfig  OBJECT IDENTIFIER ::= { tcpProtocols 3 }


       smtpServerNameOrIPAddress     OBJECT-TYPE
                    SYNTAX  OCTET STRING (SIZE(0..64))
                    ACCESS  read-write
                    STATUS  mandatory
                    DESCRIPTION
                    "A NULL terminated 64 byte string that contains the
                    SMTP server Host name or IP address(a.b.c.d)."
                    ::= { smtpConfig 1 }

       attachmentsToEmailAlerts  OBJECT-TYPE
                    SYNTAX  INTEGER {
                      noAttachments(0),
                      attachEventLog(1)
                    }
                    ACCESS  read-write
                    STATUS  mandatory
                    DESCRIPTION
                    "Indicates if the event log should be attached to
                    a email alert."
                    ::= { smtpConfig 2 }

     -- ***********************************************************************
     -- Telnet Configuration
     -- ***********************************************************************

        -- 4.9.3.4.1
        tcpApplicationConfig  OBJECT IDENTIFIER ::= { tcpProtocols 4 }
--         telnetInactivityTimeout  OBJECT-TYPE
--                      SYNTAX  INTEGER
--                      ACCESS  read-write
--                      STATUS  mandatory
--                      DESCRIPTION
--                      "Default is 120 seconds. Value of zero is no timeout.
--                      Max value is any positive 4 bytes value."
--                      ::= { tcpApplicationConfig 1 }

        -- 4.9.3.4.2
         commandModeInactivityTimeout  OBJECT-TYPE
                      SYNTAX  INTEGER
                      ACCESS  read-write
                      STATUS  mandatory
                      DESCRIPTION
                      "Default is zero means no timeout. Max value is any positive 4 bytes value."
                      ::= { tcpApplicationConfig 2 }

        -- 4.9.3.4.3
         telnetConnectionCounts   OBJECT-TYPE
                      SYNTAX  INTEGER {
                        disabled(0),
                        one(1),
                        two(2)
                      }
                      ACCESS  read-write
                      STATUS  mandatory
                      DESCRIPTION
                      "The number of telnet connections that can be active
                      concurrently."
                      ::= { tcpApplicationConfig 3 }

        -- 4.9.3.4.4
         commandMode  OBJECT-TYPE
                      SYNTAX  INTEGER {
                        disabled(0),
                        enabled(1)
                      }
                      ACCESS  read-write
                      STATUS  mandatory
                      DESCRIPTION
                      "Disable/Enable TCP Command Mode."
                      ::= { tcpApplicationConfig 4 }

        -- 4.9.3.4.5
         slpAddrType  OBJECT-TYPE
                      SYNTAX  INTEGER {
                        multicast(0),
                        broadcast(1)
                      }
                      ACCESS  read-write
                      STATUS  mandatory
                      DESCRIPTION
                      "Set SLP address type to 0 (multicast) or 1 (broadcast). Note that when
                      slpAddrType is set to broadast value then the multicast address set in in
                      slpMulticastAddt will be ignored."
                      ::= { tcpApplicationConfig 5 }

        -- 4.9.3.4.6
         slpMulticastAddr  OBJECT-TYPE
                      SYNTAX  IpAddress
                      ACCESS  read-write
                      STATUS  mandatory
                      DESCRIPTION
                      "Service Locator Protocol Multicast address"
                      ::= { tcpApplicationConfig 6 }

     -- ***********************************************************************
     -- TCP Port Assignment
     -- ***********************************************************************
     tcpPortAssignmentCfg    OBJECT IDENTIFIER ::= { tcpProtocols 5 }

         tcpPortsRestoreDefault   OBJECT-TYPE
                      SYNTAX  INTEGER
                      ACCESS  write-only
                      STATUS  mandatory
                      DESCRIPTION
                      "HTTP port number. Default value is 80. Once changed, the url's have to
                      include :port at the end. SP has to be reset for change to take effect."
                      ::= { tcpPortAssignmentCfg 1 }

         httpPortAssignment   OBJECT-TYPE
                      SYNTAX  INTEGER
                      ACCESS  read-write
                      STATUS  mandatory
                      DESCRIPTION
                      "HTTP port number. Default value is 80. Once changed, the url's have to
                      include :port at the end. SP has to be reset for change to take effect."
                      ::= { tcpPortAssignmentCfg 2 }

         httpsPortAssignment   OBJECT-TYPE
                      SYNTAX  INTEGER
                      ACCESS  read-write
                      STATUS  mandatory
                      DESCRIPTION
                      "SSL port number. Default value is 443. Once changed, the url's have to
                      include :port at the end. SP has to be reset for change to take effect."
                      ::= { tcpPortAssignmentCfg 3 }

         telnetPortAssignment   OBJECT-TYPE
                      SYNTAX  INTEGER
                      ACCESS  read-write
                      STATUS  mandatory
                      DESCRIPTION
                      "telnet port number. Default value is 23. SP has to be reset for change
                      to take effect."
                      ::= { tcpPortAssignmentCfg 4 }

         sshPortAssignment   OBJECT-TYPE
                      SYNTAX  INTEGER
                      ACCESS  read-write
                      STATUS  mandatory
                      DESCRIPTION
                      "SSH port number. Default value is 22. SP has to be reset for change
                      to take effect."
                      ::= { tcpPortAssignmentCfg 5 }

         snmpAgentPortAssignment   OBJECT-TYPE
                      SYNTAX  INTEGER
                      ACCESS  read-write
                      STATUS  mandatory
                      DESCRIPTION
                      "SNMP Agent port number. Default value is 161. SP has to be reset for change
                      to take effect."
                      ::= { tcpPortAssignmentCfg 6 }

         snmpTrapsPortAssignment   OBJECT-TYPE
                      SYNTAX  INTEGER
                      ACCESS  read-write
                      STATUS  mandatory
                      DESCRIPTION
                      "SNMP Traps port number. Default value is 162. SP has to be reset for change
                      to take effect."
                      ::= { tcpPortAssignmentCfg 7 }

         remvidPortAssignment   OBJECT-TYPE
                      SYNTAX  INTEGER
                      ACCESS  read-write
                      STATUS  mandatory
                      DESCRIPTION
                      "Remote Console port number. Default value is 2000. SP has to be reset for change
                      to take effect."
                      ::= { tcpPortAssignmentCfg 8 }

         tcpcmdPortAssignment   OBJECT-TYPE
                      SYNTAX  INTEGER
                      ACCESS  read-write
                      STATUS  mandatory
                      DESCRIPTION
                      "TCP Command Mode port number. Default value is 6090. SP has to be reset for change
                      to take effect."
                      ::= { tcpPortAssignmentCfg 9 }

         tcpcmdPortAssignment   OBJECT-TYPE
                      SYNTAX  INTEGER
                      ACCESS  read-write
                      STATUS  mandatory
                      DESCRIPTION
                      "Windows Terminal Services port number. Default value is 3389. SP has to be reset for change
                      to take effect."
                      ::= { tcpPortAssignmentCfg 10 }


     -- ***********************************************************************
     -- LDAP Clinet Configuration
     -- ***********************************************************************

     ldapClientCfg    OBJECT IDENTIFIER ::= { tcpProtocols 6 }

         ldapServer1NameOrIPAddress     OBJECT-TYPE
                      SYNTAX  OCTET STRING (SIZE(0..64))
                      ACCESS  read-write
                      STATUS  mandatory
                      DESCRIPTION
                      "A NULL terminated 64 byte string that contains the
                      LDAP server host name or IP address (a.b.c.d)."
                      ::= { ldapClientCfg 1 }

         ldapServer1PortNumber   OBJECT-TYPE
                      SYNTAX  INTEGER
                      ACCESS  read-write
                      STATUS  mandatory
                      DESCRIPTION
                      "LDAP server port number."
                      ::= { ldapClientCfg 2 }

         ldapServer2NameOrIPAddress     OBJECT-TYPE
                      SYNTAX  OCTET STRING (SIZE(0..64))
                      ACCESS  read-write
                      STATUS  mandatory
                      DESCRIPTION
                      "A NULL terminated 64 byte string that contains the
                      LDAP server host name or IP address (a.b.c.d)."
                      ::= { ldapClientCfg 3 }

         ldapServer2PortNumber   OBJECT-TYPE
                      SYNTAX  INTEGER
                      ACCESS  read-write
                      STATUS  mandatory
                      DESCRIPTION
                      "LDAP server port number."
                      ::= { ldapClientCfg 4 }

         ldapServer3NameOrIPAddress     OBJECT-TYPE
                      SYNTAX  OCTET STRING (SIZE(0..64))
                      ACCESS  read-write
                      STATUS  mandatory
                      DESCRIPTION
                      "A NULL terminated 64 byte string that contains the
                      LDAP server host name or IP address (a.b.c.d)."
                      ::= { ldapClientCfg 5 }

         ldapServer3PortNumber   OBJECT-TYPE
                      SYNTAX  INTEGER
                      ACCESS  read-write
                      STATUS  mandatory
                      DESCRIPTION
                      "LDAP server port number."
                      ::= { ldapClientCfg 6 }

         ldapRootDN     OBJECT-TYPE
                      SYNTAX  OCTET STRING (SIZE(0..64))
                      ACCESS  read-write
                      STATUS  mandatory
                      DESCRIPTION
                      "Distinguished Name for root entry of directory tree.
                      An example might look like dn=foobar,dn=com."
                      ::= { ldapClientCfg 7 }

         ldapUserSearchBaseDN     OBJECT-TYPE
                      SYNTAX  OCTET STRING (SIZE(0..64))
                      ACCESS  read-write
                      STATUS  mandatory
                      DESCRIPTION
                      "As part of the user authentication process, it is necessary to search
                      the LDAP server for one or more attributes associated with a particular
                      user. Any search request must specify the base DN for the actual search.
                      This field specifies the base DN which should be used to search the User
                      directory. An example might look like cn=users,dn=foobar,dn=com. If this
                      field is left blank, the Root DN will be used as the search base instead.
                      As mentioned, user searches are part of the authentication process. They
                      are carried out to retrieve information about the user such as login
                      permissions, callback number, and group memberships. For Version 2.0 LDAP
                      clients, it is strongly encouraged that this parameter be configured,
                      otherwise a search using the root DN may not succeed (as seen on Active
                      Directory servers)."
                      ::= { ldapClientCfg 8 }

         ldapGroupFilter     OBJECT-TYPE
                      SYNTAX  OCTET STRING (SIZE(0..64))
                      ACCESS  read-write
                      STATUS  mandatory
                      DESCRIPTION
                      "This filter is used for group authentication. It specifies what group or
                      groups that this MM belongs to. If left blank, group authentication is
                      disabled. Otherwise, group authentication will be performed against the
                      filter. The filter can be a specific group name (eg. RSAWest), a wildcard (*)
                      which matches everything, or a wildcard with a prefix (eg. RSA*). The default
                      filter is RSA*.
                      After user authentication, group authentication will take place, whereby an
                      attempt will be made to match the group or groups (that the user belongs to)
                      to the group filter defined here. If there is no match, the user will not pass
                      authentication and will be blocked. If there is a match, the login permissions
                      for the user will be retrieved from the matched group(s), unless the user
                      already has login permissions assigned directly from the user record retrieved
                      from the LDAP server."
                      ::= { ldapClientCfg 9 }

         ldapBindingMethod  OBJECT-TYPE
                      SYNTAX  INTEGER {
                        anonymousAuthentication(0),
                        clientAuthentication(1),
                        userPrincipalName(2),
                        strictUserPrincipalName(3)
                      }
                      ACCESS  read-write
                      STATUS  mandatory
                      DESCRIPTION
                      "On initial binds to the LDAP server during user authentication, there are
                      three options:
                      Anonymous authentication: Bind attempt is made without a client DN or password.
                      If the bind is successful, a search will be requested in order to find an entry
                      on the LDAP server for the user attempting to login. If an entry is found, a
                      second attempt to bind will be attempted, this time with the user's DN and
                      password. If this succeeds, the user is deemed to have passed the user
                      authentication phase. Group authentication is then attempted if it is enabled.
                      Client authentication: Bind attempt is made with client DN and password
                      specified by this configuration parameter. If the bind is successful, we
                      proceed as above.
                      User Principal Name (UPN): Bind attempt is made directly with the credentials
                      used during the login process. If this succeeds, the user is deemed to have
                      passed the user authentication phase. Note that for Active Directory servers,
                      the userid can have the form someuser@somedomain or simply someuser.
                      Strict UPN: This is the same as UPN above, except that the userid must have
                      the form someuser@somedomain. The string entered by the user will be parsed
                      for the @ symbol."
                      ::= { ldapClientCfg 10 }

         ldapClientAuthenticationDN     OBJECT-TYPE
                      SYNTAX  OCTET STRING (SIZE(0..64))
                      ACCESS  read-write
                      STATUS  mandatory
                      DESCRIPTION
                      "The initial bind to the LDAP server during user authentication can be
                      performed with anonymous authentication, client based authentication, or UPN.
                      The client based option requires a client DN and password as parameters to
                      the bind request. These parameters are configured here. Note that the password
                      can be left blank."
                      ::= { ldapClientCfg 11 }

         ldapClientAuthenticationPassword     OBJECT-TYPE
                      SYNTAX  OCTET STRING (SIZE(0..16))
                      ACCESS  read-write
                      STATUS  mandatory
                      DESCRIPTION
                      "The client authentication password"
                      ::= { ldapClientCfg 12 }

         ldapUIDsearchAttribute     OBJECT-TYPE
                      SYNTAX  OCTET STRING (SIZE(0..64))
                      ACCESS  read-write
                      STATUS  mandatory
                      DESCRIPTION
                      "When the binding method selected is Anonymous authentication or Client
                      authentication, the initial bind to the LDAP server is followed by a search
                      request aimed at retrieving specific information about the user, including the
                      user's DN, login permissions, and group ownerships. In order to retrieve this
                      information, the search request must specify the attribute name used to
                      represent userids on that server. Specifically, this name is used as a search
                      filter against the login id entered by the user. This attribute name is
                      configured here. If this field is left blank, a default of uid is used during
                      user authentication.
                      For example, on Active Directory servers, the attribute name used for userids
                      is often sAMAccoutName.
                      When the binding method selected is UPN or Strict UPN, this field defaults
                      automatically to userPrincipalName during user authentication if the userid
                      entered has the form userid@somedomain."
                      ::= { ldapClientCfg 13 }

         ldapGroupSearchAttribute     OBJECT-TYPE
                      SYNTAX  OCTET STRING (SIZE(0..64))
                      ACCESS  read-write
                      STATUS  mandatory
                      DESCRIPTION
                      "When the MM Group Filter name is configured, it is necessary to retrieve
                      from the LDAP server the list of groups that a particular user belongs to.
                      This is required to do group authentication. In order to retrieve this list,
                      the search filter sent to the server must specify the attribute name associated
                      with groups. This field specifies this attribute name.
                      If this field is left blank, the attribute name in the filter will default
                      to memberOf."
                      ::= { ldapClientCfg 14 }

         ldapLoginPermissionAttribute     OBJECT-TYPE
                      SYNTAX  OCTET STRING (SIZE(0..64))
                      ACCESS  read-write
                      STATUS  mandatory
                      DESCRIPTION
                      "When a user successfully authenticates via a LDAP server, it is necessary
                      to retrieve the login permissions for this user. In order to retrieve these
                      permissions, the search filter sent to the server must specify the attribute
                      name associated with login permissions. This field specifies this attribute
                      name."
                      ::= { ldapClientCfg 15 }

         ldapUseDNSOrPreConfiguredServers     OBJECT-TYPE
                      SYNTAX  INTEGER {
                        usePreConfiguredLDAPServers (0),
                        useDNSToFindLDAPServers (1)
                      }
                      ACCESS  read-write
                      STATUS  mandatory
                      DESCRIPTION
                      "The MM contains a Version 2.0 LDAP Client that may be configured to provide
                      user authentication through one or more LDAP servers. The LDAP server(s) to be
                      used for authentication can be discovered dynamically or manually pre-configured.

                      If the usePreConfiguredLDAPServers option is selected, up to 3 LDAP servers can
                      be configured. Simply enter the server's IP address or hostname (assuming DNS
                      is enabled).  The port number for each server is optional. If left blank,
                      the default value of 389 is used for non-secured LDAP connections. For secured
                      connections, the default is 636. At least one server must be configured.

                      If the useDNSToFindLDAPServers is selected, the mechanisms described by RFC2782
                      (A DNS RR for specifying the location of services) are applied to find the
                      server(s). This is known as DNS SRV."
                      ::= { ldapClientCfg 16 }

         ldapDomainSource     OBJECT-TYPE
                      SYNTAX  INTEGER {
                        extractSearchDomainFromLoginID (0),
                        useOnlyConfiguredSearchDomainBelow (1),
                        tryLoginFirstThenConfiguredValue (2)
                      }
                      ACCESS  read-write
                      STATUS  mandatory
                      DESCRIPTION
                      "The DNS SRV request sent to the DNS server must specify a domain name.
                      The LDAP client will determine where to get this domain name based on one
                      of the following three options:

                        - extractSearchDomainFromLoginID: With this option, the LDAP client will
                      use the domain name in the login id. For example, if the login id is
                      joesmith@mycompany.com, the domain name equals mycompany.com. If the domain
                      name cannot be extracted, the DNS SRV will fail, causing the user
                      authentication to fail automatically.

                        - useOnlyConfiguredSearchDomainBelow: With this option, the LDAP client
                      will use the domain name configured in the Search Domain parameter.

                        - tryLoginFirstThenConfiguredValue: With this option, the LDAP client will
                      first attempt to extract the domain name from the login id. If this succeeds,
                      this domain name will be used in the DNS SRV request. If there is no domain
                      name present in the login id, the LDAP client will instead use the configured
                      Search Domain parameter as the domain name in the DNS SRV request.
                      If nothing is configured, user authentication will fail immediately."
                      ::= { ldapClientCfg 17 }

         ldapSearchDomain     OBJECT-TYPE
                      SYNTAX  OCTET STRING (SIZE(0..64))
                      ACCESS  read-write
                      STATUS  mandatory
                      DESCRIPTION
                      "This parameter may be used as the domain name in the DNS SRV request,
                      depending on how the Domain Source parameter is configured."
                      ::= { ldapClientCfg 18 }

         ldapServiceName     OBJECT-TYPE
                      SYNTAX  OCTET STRING (SIZE(0..16))
                      ACCESS  read-write
                      STATUS  mandatory
                      DESCRIPTION
                      "The DNS SRV request sent to the DNS server must also specify a service name.
                      The configured value will be used for this purpose. If left blank, the default
                      value used is 'ldap'. Note that the DNS SRV request must also specify a protocol
                      name. This defaults to 'tcp' and is not configurable."
                      ::= { ldapClientCfg 19 }


        -- ********************************************************************************
        -- NTP Configuration
        -- ********************************************************************************
        ntpConfig  OBJECT IDENTIFIER ::= { tcpProtocols 8 }
        
        -- 4.9.3.8.1
         ntpEnable    OBJECT-TYPE
                      SYNTAX  INTEGER {
                        disabled(0),
                        enabled(1)
                      }
                      ACCESS  read-write
                      STATUS  mandatory
                      DESCRIPTION
                      "Disable/Enable the NTP client.  The client will update
                      the ASM system clock at the frequency specified."
                      ::= { ntpConfig 1 }

        -- 4.9.3.8.2
         ntpIpAddressHostname  OBJECT-TYPE
                      SYNTAX  OCTET STRING (SIZE(0..63))
                      ACCESS  read-write
                      STATUS  mandatory
                      DESCRIPTION
                      "NTP server's IP address or hostname if DNS is enabled
                      and configured."
                      ::= { ntpConfig 2 }
                                    
        -- 4.9.3.8.3
         ntpUpdateFrequency  OBJECT-TYPE
                      SYNTAX  INTEGER
                      ACCESS  read-write
                      STATUS  mandatory
                      DESCRIPTION
                      "The frequency in minutes that the NTP service runs.
                      The value range is 1 to 65535."
                      ::= { ntpConfig 3 }
                      
        -- 4.9.3.8.5
         ntpUpdateClock  OBJECT-TYPE
                      SYNTAX  INTEGER  {
                        execute(1)
                      }  
                      ACCESS  read-write
                      STATUS  mandatory
                      DESCRIPTION
                      "Update the ASM system clock with the specified NTP server.
                      A valid NTP server must be configured first."
                      ::= { ntpConfig 5 }

                      
    -- ***********************************************************************
    -- SP Host OS Platform
    -- ***********************************************************************
    spHostOs      OBJECT IDENTIFIER ::= { configureSP 12 }

     spHostOsPlatform      OBJECT-TYPE
                           SYNTAX  INTEGER {
                             other(1),
                             linux(2)
                           }
                           ACCESS  read-write
                           STATUS  mandatory
                           DESCRIPTION
                           "Host Operation System Flatform."
                           ::= { spHostOs 1 }

-- ***********************************************************************
--  System Services
-- ***********************************************************************
    -- ***********************************************************************
    -- System Watch Dog Timers
    -- ***********************************************************************
    serverTimers OBJECT IDENTIFIER ::= { generalSystemSettings 1 }

     serverPost   OBJECT-TYPE
                  SYNTAX  INTEGER {
                    disabled(0),
                    threeAndHalfMinutes(7),
                    fourMinutes(8),
                    fourAndHalfMinutes(9),
                    fiveMinutes(10),
                    sevenAndHalfMinutes(15),
                    tenMinutes(20),
                    fifteenMinutes(30),
                    twentyMinutes(40),
                    thirtyMinutes(60),
                    oneHour(120),
                    twoHours(240)
                   }
                   ACCESS  read-write
                   STATUS  mandatory
                   DESCRIPTION
                   "Number in 30 second intervals the ASM will wait
                   for the server to complete power on self test(POST).
                   If the system fails to complete
                   POST within this time, the ASM will generate a
                   POST timeout alert(if enabled) and automatically restart the system
                   one time. Once the system is restarted, the POST
                   watchdog is automatically disabled until the operating system is
                   shutdown and the server is power cycled."
                   ::= { serverTimers 1 }

     oSHang       OBJECT-TYPE
                  SYNTAX  INTEGER {
                    disabled(0),
                    twoAndHalfMinutes(150),
                    threeMinutes(180),
                    threeAndHalfMinutes(210),
                    fourMinutes(240)
                   }
                   ACCESS  read-write
                   STATUS  mandatory
                   DESCRIPTION
                   "Number, in 1 second intervals, the ASM will
                   check to insure the OS is operating properly.
                   If the operating system fails to respond within 6 seconds to one
                   of these checks, the remote supervisor adapter will generate
                   an O/S Timeout alert(if enabled) and automatically restart the
                   system one time. Once the system is restarted, the O/S Watchdog
                   is automatically disabled until the operating
                   system is shutdown and the server is power cycled."
                   ::= { serverTimers 2 }

     oSLoader     OBJECT-TYPE
                  SYNTAX  INTEGER {
                    disabled(0),
                    oneHalfMinutes(1),
                    oneMinutes(2),
                    oneAndHalfMinutes(3),
                    twoMinutes(4),
                    twoAndHalfMinutes(5),
                    threeMinutes(6),
                    fourMinutes(8),
                    fourAndHalfMinutes(9),
                    fiveMinutes(10),
                    fiveAndHalfMinutes(11),
                    sevenAndHalfMinutes(15),
                    tenMinutes(20),
                    fifteenMinutes(30),
                    twentyMinutes(40),
                    thirtyMinutes(60),
                    oneHour(120),
                    twoHours(240)
                   }
                   ACCESS  read-write
                   STATUS  mandatory
                   DESCRIPTION
                   "Number in 30 second intervals the remote ASM will wait
                   between completion of POST and the end of loading the OS.
                   If this interval is exceeded, the ASM will
                   generate a Loader Timeout alert(if enabled) and automatically restart
                   the system one time. Once the system is restarted, the
                   Loader Timeout is automatically disabled until the operating
                   system is shutdown and the server is power cycled."
                   ::= { serverTimers 3 }

    -- ***********************************************************************
    -- Events Sent to local Operating System
    -- ***********************************************************************
    localEvents OBJECT IDENTIFIER ::= { generalSystemSettings 2 }

     eventTemp    OBJECT-TYPE
                  SYNTAX  INTEGER {
                    disabled(0),
                    enabled(1)
                  }
                  ACCESS  read-write
                  STATUS  mandatory
                  DESCRIPTION
                  "Generate a event to the local OS running IBM Director
                  application if any monitored temperature sensor exceed the threshold value."
                  ::= { localEvents 1 }

     eventVoltage OBJECT-TYPE
                  SYNTAX  INTEGER {
                    disabled(0),
                    enabled(1)
                  }
                  ACCESS  read-write
                  STATUS  mandatory
                  DESCRIPTION
                  "Generate a event to the local OS running IBM Director
                  application if any monitored voltage sensor exceed the threshold value."
                  ::= { localEvents 2 }

     eventRedundantPwrSupply  OBJECT-TYPE
                  SYNTAX  INTEGER {
                    disabled(0),
                    enabled(1)
                  }
                  ACCESS  read-write
                  STATUS  mandatory
                  DESCRIPTION
                  "Generate a event to the local OS running IBM Director
                  application if a redundant power supply fails."
                  ::= { localEvents 3 }

     eventPowerOff  OBJECT-TYPE
                  SYNTAX  INTEGER {
                    disabled(0),
                    enabled(1)
                  }
                  ACCESS  read-write
                  STATUS  mandatory
                  DESCRIPTION
                  "Generate a event to the local OS running the IBM Director
                  application if the system is powered off."
                  ::= { localEvents 4 }

     eventRemoteLogin  OBJECT-TYPE
                  SYNTAX  INTEGER {
                    disabled(0),
                    enabled(1)
                  }
                  ACCESS  read-write
                  STATUS  mandatory
                  DESCRIPTION
                  "Generate a event to the local OS running the IBM Director
                  application if a user logs into the ASM."
                  ::= { localEvents 6 }

     eventTamper   OBJECT-TYPE
                   SYNTAX  INTEGER {
                     disabled(0),
                     enabled(1)
                   }
                   ACCESS  read-write
                   STATUS  mandatory
                   DESCRIPTION
                   "Generate a event to the local OS running the IBM Director
                   application if physical intrusion of the box is detected.
                   Will only happen if the system contains physical intrusion
                   detection hardware."
                   ::= { localEvents 7 }

     eventErrorLogFull OBJECT-TYPE
                   SYNTAX  INTEGER {
                     disabled(0),
                     enabled(1)
                   }
                   ACCESS  read-write
                   STATUS  mandatory
                   DESCRIPTION
                   "Generate a event to the local OS running the IBM Director
                   application if the event log becomes full."
                   ::= { localEvents 8 }

     eventFan      OBJECT-TYPE
                   SYNTAX  INTEGER {
                     disabled(0),
                     enabled(1)
                   }
                   ACCESS  read-write
                   STATUS  mandatory
                   DESCRIPTION
                   "Generate a event to the local OS running the IBM Director
                   application if one or more cooling fans fail."
                   ::= { localEvents 9 }

     eventPowerSupply OBJECT-TYPE
                   SYNTAX  INTEGER {
                     disabled(0),
                     enabled(1)
                   }
                   ACCESS  read-write
                   STATUS  mandatory
                   DESCRIPTION
                   "Generate a event to the local OS running the IBM Director
                   application if a power supply fails."
                   ::= { localEvents 10 }

     eventDASD     OBJECT-TYPE
                   SYNTAX  INTEGER {
                     disabled(0),
                     enabled(1)
                   }
                   ACCESS  read-write
                   STATUS  mandatory
                   DESCRIPTION
                   "Generate a event to the local OS running the IBM Director
                   application if a hard drive fails."
                   ::= { localEvents 11 }

     eventErrorLog75PercentFull OBJECT-TYPE
                   SYNTAX  INTEGER {
                     disabled(0),
                     enabled(1)
                   }
                   ACCESS  read-write
                   STATUS  mandatory
                   DESCRIPTION
                   "Generate a event to the local OS running the IBM Director
                   application if the event log becomes 75% full."
                   ::= { localEvents 12 }

     eventPFA      OBJECT-TYPE
                   SYNTAX  INTEGER {
                     disabled(0),
                     enabled(1)
                   }
                   ACCESS  read-write
                   STATUS  mandatory
                   DESCRIPTION
                   "Generate a event to the local OS running IBM Director
                   application if hardware detects a Predictive Failure
                   Analysis(PFA) on PFA enabled hardware."
                   ::= { localEvents 13 }

     eventPartitionCFG      OBJECT-TYPE
                            SYNTAX  INTEGER {
                              disabled(0),
                              enabled(1)
                            }
                            ACCESS  read-write
                            STATUS  mandatory
                            DESCRIPTION
                            "Generate a event to the local OS running IBM Director
                            application if hardware detects a Partition Configuration."
                            ::= { localEvents 15 }


    -- ***********************************************************************
    -- PXE Boot
    -- ***********************************************************************
    networkPXEboot OBJECT-TYPE
                   SYNTAX  INTEGER {
                     networkPXEBootDisabled(0),
                     networkPXEBootEnabled(1)
                   }
                   ACCESS  read-write
                   STATUS  mandatory
                   DESCRIPTION
                   "Modify the system's boot sequence for the next system restart
                   in order to attempt a PXE/DHCP network boot.  The system's boot
                   sequence(set via the BIOS settings) will be altered only if the
                   system is not under PAP (Privileged Access Protection)."
                   ::= { generalSystemSettings 3 }

    -- ***********************************************************************
    -- NMI Reset Delay
    -- ***********************************************************************
    nmiResetDelay  OBJECT-TYPE
                   SYNTAX  INTEGER {
                    disabled(0),
                    oneHalfMinutes(30),
                    oneMinutes(60),
                    oneAndHalfMinutes(90),
                    twoMinutes(120),
                    twoAndHalfMinutes(150),
                    threeMinutes(180),
                    threeAndHalfMinutes(210),
                    fourMinutes(240)
                   }
                   ACCESS  read-write
                   STATUS  mandatory
                   DESCRIPTION
                   "The number of 1 second intervals the ASM will
                   wait after the system has generated a NMI(Non-Maskable Interrupt)
                   before automatically restarting the system. NMIs generally
                   occur due to a severe hardware fault."
                   ::= { generalSystemSettings 11 }


    -- ***********************************************************************
    -- Miscelaneous
    -- ***********************************************************************
    disallowCmdOnUSBItf  OBJECT-TYPE
                   SYNTAX  INTEGER {
                    allowCmd(0),
                    disallowCmd(1)
                   }
                   ACCESS  read-write
                   STATUS  mandatory
                   DESCRIPTION
                   "This controls whether the commands received on the USB interface
                   are allowed or not.  When this is set to disallowCmd(1), all
                   commands received on the USB interface are rejected."
                   ::= { generalSystemSettings 12 }


-- ***********************************************************************
--  System Power Control
-- ***********************************************************************

    -- ***********************************************************************
    -- Power Statistics for the system
    -- ***********************************************************************
    powerStatistics OBJECT IDENTIFIER ::= { systemPower 1 }
     currentSysPowerStatus  OBJECT-TYPE
                    SYNTAX  INTEGER {
                      poweredOff(0),
                      poweredOn(255)
                    }
                    ACCESS  read-only
                    STATUS  mandatory
                    DESCRIPTION
                    "Indicates if the system is currently powered on or off."
                    ::= { powerStatistics 1 }


     powerOnHours   OBJECT-TYPE
                    SYNTAX  INTEGER
                    ACCESS  read-only
                    STATUS  mandatory
                    DESCRIPTION
                    "Number of hours the system has been powered on."
                    ::= { powerStatistics 2 }

     restartCount   OBJECT-TYPE
                    SYNTAX  INTEGER
                    ACCESS  read-only
                    STATUS  mandatory
                    DESCRIPTION
                    "Number of times the system has been restarted."
                    ::= { powerStatistics 3 }

     systemState OBJECT-TYPE
                    SYNTAX  INTEGER {
                      systemPowerOffStateUnknown(0),
                      inPOST(1),
                      stoppedInPOSTEerrorDetected(2),
                      bootedFlashOrSystemPartition(3),
                      bootingOSorInOS(4),
                      inOS(5),
                      cpuIsHeldInReset(6),
                      systemPowerOnBeforePOST(7)
                    }
                    ACCESS  read-only
                    STATUS  mandatory
                    DESCRIPTION
                    "Shows the current operational state of the system."
                    ::= { powerStatistics 4 }

    -- ***********************************************************************
    -- System Power off configuration
    -- ***********************************************************************
    powerSysConfig OBJECT IDENTIFIER ::= { systemPower 2 }


     powerSysOffDelay OBJECT-TYPE
                   SYNTAX  INTEGER {
                     noDelay(0),
                     oneHalfMinute(30),
                     oneMinute(60),
                     twoMinutes(120),
                     threeMinutes(180),
                     fourMinutes(240),
                     fiveMinute(300),
                     sixMinutes(360),
                     sevenAndHalfMinutes(450),
                     tenMinutes(600),
                     fifteenMinutes(900),
                     twentyMinutes(1200),
                     thirtyMinutes(1800),
                     oneHour(3600),
                     twoHours(7200)
                   }
                   ACCESS  read-write
                   STATUS  mandatory
                   DESCRIPTION
                   "The number of 1 second intervals the ASM will
                   wait before powering off the system."
                   ::= { powerSysConfig 1 }


     powerSysOnClockSetting OBJECT-TYPE
                   SYNTAX  OCTET STRING
                   ACCESS  read-write
                   STATUS  mandatory
                   DESCRIPTION
                   "The clock setting used to determine when the remote supervisor adapter
                   will power on the system. The examples and the format follow:

                   (1)For example to set the value so the system will power on
                   March 4, 2001 at 06:00AM set the value to: '03/04/2001,06:00'.
                   In order to insure correct operation, it is advisable for the
                   user to read the date and time of the remote supervisor adapter
                   clock before setting this value to a future time.
                   (2)Setting the reset value will cause the
                   power off timer to be reset and be deactivated. For example
                   to reset the clock set the value to: '01/01/1990,00:00',

                   field  contents         range
                   _____  ________         _____
                    1     month           01..12 (reset value - 01)
                    2     separator       '/'
                    3     day             01..31 (reset value - 01)
                    4     separator       '/'
                    5     year            1990..2089 (reset value - 1990)
                    6     separator       ','
                    7     hour            00..23 (reset value - 00)
                    8     separator       ':'
                    9     minutes         00..59 (reset value - 00)
                   "
                   ::= { powerSysConfig 2 }

    -- ***********************************************************************
    -- System Power off control
    -- ***********************************************************************
    powerOffSystemControl OBJECT IDENTIFIER ::= { systemPower 3 }

     powerOffWithOsShutdown  OBJECT-TYPE
                   SYNTAX  INTEGER {
                    execute(1)
                   }
                   ACCESS   write-only
                   STATUS  mandatory
                   DESCRIPTION
                   "Power off the system after performing a OS shutdown."
                   ::= { powerOffSystemControl 1 }

     powerOffImmediately  OBJECT-TYPE
                   SYNTAX  INTEGER {
                    execute(1)
                   }
                   ACCESS   write-only
                   STATUS  mandatory
                   DESCRIPTION
                   "Power off the system immediately."
                   ::= { powerOffSystemControl 2 }

    -- ***********************************************************************
    -- System Power on control
    -- ***********************************************************************
    powerOnSystemControl OBJECT IDENTIFIER ::= { systemPower 4 }

     powerOnImmediately  OBJECT-TYPE
                   SYNTAX  INTEGER {
                    execute(1)
                   }
                   ACCESS  write-only
                   STATUS  mandatory
                   DESCRIPTION
                   "Power on the system immediately."
                   ::= { powerOnSystemControl 2 }


-- ***********************************************************************
--  Restart Control
-- ***********************************************************************

    shutdownOsThenRestart  OBJECT-TYPE
                   SYNTAX  INTEGER {
                    execute(1)
                   }
                   ACCESS  write-only
                   STATUS  mandatory
                   DESCRIPTION
                   "Shutdown the OS and then restart the system and boot the OS."
                   ::= { restartReset 1 }

    restartSystemImmediately  OBJECT-TYPE
                   SYNTAX  INTEGER {
                    execute(1)
                   }
                   ACCESS  write-only
                   STATUS  mandatory
                   DESCRIPTION
                   "Restart the system immediately and then the boot OS."
                   ::= { restartReset 2 }


    restartSPImmediately  OBJECT-TYPE
                   SYNTAX  INTEGER {
                    execute(1)
                   }
                   ACCESS  write-only
                   STATUS  mandatory
                   DESCRIPTION
                   "Restart the ASM immediately."
                   ::= { restartReset 4 }

    resetSPConfigAndRestart  OBJECT-TYPE
                  SYNTAX  INTEGER {
                    execute(1)
                   }
                  ACCESS  write-only
                  STATUS  mandatory
                  DESCRIPTION
                  "Will cause all the ASM information to
                  be reset to it's initial factory defaults(all previous
                  configuration information is lost) and the ASM
                  will be re-started."
                  ::= { restartReset 20 }



-- ***********************************************************************
--  Firmware Update
-- ***********************************************************************
    firmwareUpdateTarget  OBJECT-TYPE
                  SYNTAX  INTEGER {
                    asmCard(0)
                  }
                  ACCESS  read-write
                  STATUS  mandatory
                  DESCRIPTION
                  "Target module whose firmware will be updated."
                  ::= { firmwareUpdate 1 }

    firmwareUpdateTftpServer   OBJECT-TYPE
                  SYNTAX  OCTET STRING (SIZE(0..63))
                  ACCESS  read-write
                  STATUS  mandatory
                  DESCRIPTION
                  "IP address of the TFTP server where the firmware file resides.
                  The address must be entered in a dotted decimal IP string
                  (eg. 9.37.44.2)."
                  ::= { firmwareUpdate 2 }

    firmwareUpdateFileName   OBJECT-TYPE
                  SYNTAX  OCTET STRING (SIZE(0..63))
                  ACCESS  read-write
                  STATUS  mandatory
                  DESCRIPTION
                  "File name of the firmware file."
                  ::= { firmwareUpdate 3 }

    firmwareUpdateStart   OBJECT-TYPE
                  SYNTAX INTEGER {
                    execute(1)
                  }
                  ACCESS  write-only
                  STATUS  mandatory
                  DESCRIPTION
                  "Start updating the firmware of the specified RSA Card.
                  Note 1: The firmware update might take up to several
                  minutes to complete.  Do not reset the RSA Card until
                  the control has been returned.  At this point, the results
                  will be displayed.
                  Note 2: Use firmwareUpdateStatus to confirm the status of
                  the last firmware update initiated by SNMP method.  The
                  RSA Card must be restarted for the new firmware to
                  take affect."
                  ::= { firmwareUpdate 4 }


    firmwareUpdateStatus  OBJECT-TYPE
                  SYNTAX OCTET STRING
                  ACCESS  read-only
                  STATUS  mandatory
                  DESCRIPTION
                  "Get the status of the last firmware update which was
                  initiated through SNMP method."
                  ::= { firmwareUpdate 5 }


-- ***********************************************************************
-- PCI-X Expansion Enclosure(Box) Table
-- ***********************************************************************

     pcixExpansionBoxTable  OBJECT-TYPE
                           SYNTAX  SEQUENCE OF PcixExpansionBoxEntry
                           ACCESS  not-accessible
                           STATUS  mandatory
                           DESCRIPTION
                           "Table of PCI-X Expansion Enclosure(s)."
                           ::= { pcixExpansionBox 1 }

     pcixExpansionBoxEntry  OBJECT-TYPE
                           SYNTAX  PcixExpansionBoxEntry
                           ACCESS  not-accessible
                           STATUS  mandatory
                           DESCRIPTION
                           "PCI-X expansion enclosure entry."
                           INDEX { pcixExpansionBoxEntryIndex }
                           ::= { pcixExpansionBoxTable 1 }

     PcixExpansionBoxEntry ::= SEQUENCE {
                  pcixExpansionBoxEntryIndex INTEGER,
                  pcixExpansionBoxEntryName OCTET STRING,
                  pcixExpansionBoxEntryStatus INTEGER,
                  pcixExpansionBoxEntryEnclosureSerialNumber OCTET STRING
     }



     pcixExpansionBoxEntryIndex  OBJECT-TYPE
                           SYNTAX  INTEGER(0..255)
                           ACCESS  read-only
                           STATUS  mandatory
                           DESCRIPTION
                           "PCI-X expansion enclosure index."
                           ::= { pcixExpansionBoxEntry 1 }

     pcixExpansionBoxEntryName  OBJECT-TYPE
                           SYNTAX  OCTET STRING
                           ACCESS  read-only
                           STATUS  mandatory
                           DESCRIPTION
                           "Null terminated string that
                           contains the individual PCI-X expansion enclosure name,
                           for example 'Expansion Enclosure 1 right(A) side'."
                           ::= { pcixExpansionBoxEntry 2 }

     pcixExpansionBoxEntryStatus  OBJECT-TYPE
                           SYNTAX  INTEGER {
                             notActive(0),
                             active(1)
                           }
                           ACCESS  read-only
                           STATUS  mandatory
                           DESCRIPTION
                           "Indicates the PCI-X expansion enclosure status."
                           ::= { pcixExpansionBoxEntry 3 }

     pcixExpansionBoxEntryEnclosureSerialNumber  OBJECT-TYPE
                           SYNTAX  OCTET STRING
                           ACCESS  read-only
                           STATUS  mandatory
                           DESCRIPTION
                           "Null terminated string that
                           contains the individual PCI-X expansion enclosure
                           serial number."
                           ::= { pcixExpansionBoxEntry 4 }

     -- ***********************************************************************
     -- PCI-X expansion enclosure temperature sensors
     -- ***********************************************************************
     expansionBoxTemperatureTable  OBJECT-TYPE
                           SYNTAX  SEQUENCE OF ExpansionBoxTemperatureEntry
                           ACCESS  not-accessible
                           STATUS  mandatory
                           DESCRIPTION
                           "Table of temperature sensors for PCI-X expansion enclosure."
                           ::= { pcixExpansionBox 2 }

     expansionBoxTemperatureEntry  OBJECT-TYPE
                           SYNTAX  ExpansionBoxTemperatureEntry
                           ACCESS  not-accessible
                           STATUS  mandatory
                           DESCRIPTION
                           "PCI-X expansion enclosure temperature threshold entries."
                           INDEX {pcixExpansionBoxEntryIndex, expansionBoxTemperatureEntryIndex }
                           ::= { expansionBoxTemperatureTable 1 }

     ExpansionBoxTemperatureEntry ::= SEQUENCE {
                  expansionBoxTemperatureEntryIndex INTEGER,
                  expansionBoxTemperatureEntryName OCTET STRING,
                  expansionBoxTemperatureEntryEnclosureSerialNumber OCTET STRING,
                  expansionBoxTemperatureEntryCurrentValue OCTET STRING,
                  expansionBoxTemperatureEntryHardShutdownValue OCTET STRING,
                  expansionBoxTemperatureEntrySoftShutdownValue OCTET STRING,
                  expansionBoxTemperatureEntryWarningValue OCTET STRING,
                  expansionBoxTemperatureEntryWarningResetValue OCTET STRING
      }


     expansionBoxTemperatureEntryIndex   OBJECT-TYPE
                                 SYNTAX  INTEGER
                                 ACCESS  read-only
                                 STATUS  mandatory
                                 DESCRIPTION
                                 "PCI-X Expansion temperature sensor index."
                                 ::= { expansionBoxTemperatureEntry 1 }

     expansionBoxTemperatureEntryName  OBJECT-TYPE
                                 SYNTAX  OCTET STRING
                                 ACCESS  read-only
                                 STATUS  mandatory
                                 DESCRIPTION
                                 "Null terminated string that
                                 contains the individual temperature monitor's name,
                                 for example 'Expansion Enclosure 1 right(A) side Planar'."
                                 ::= { expansionBoxTemperatureEntry 2 }

     expansionBoxTemperatureEntryEnclosureSerialNumber OBJECT-TYPE
                                 SYNTAX  OCTET STRING
                                 ACCESS  read-only
                                 STATUS  mandatory
                                 DESCRIPTION
                                 "Null terminated string that
                                 contains the individual PCI-X expansion enclosure
                                 serial number."
                                 ::= { expansionBoxTemperatureEntry 3 }

     expansionBoxTemperatureEntryCurrentValue OBJECT-TYPE
                                 SYNTAX  OCTET STRING
                                 ACCESS  read-only
                                 STATUS  mandatory
                                 DESCRIPTION
                                 "Temperature in degrees centigrade(C).
                                 An octet string expressed as 'sddd.dd Centigrade' where:
                                 s is the sign ('-' for negative or blank space for positive)
                                 d is a decimal digit or blank space for a leading zero.
                                 The string 'Not Readable!' indicates that the given monitor
                                  is not supported on this system."
                                 ::= { expansionBoxTemperatureEntry 4 }

     expansionBoxTemperatureEntryHardShutdownValue OBJECT-TYPE
                                 SYNTAX  OCTET STRING
                                 ACCESS  read-only
                                 STATUS  mandatory
                                 DESCRIPTION
                                 "Temperature in degrees centigrade(C).
                                 If the component's temperature rises above this value the
                                 system will be powered off immediately.
                                 If enabled, a critical alert/event will be generated.
                                 An octet string expressed as 'sddd.dd Centigrade' where:
                                 s is the sign ('-' for negative or blank space for positive)
                                 d is a decimal digit or blank space for a leading zero.
                                 The string 'Not Readable!' indicates that the given monitor
                                 is not supported on this system."
                                 ::= { expansionBoxTemperatureEntry 5 }

     expansionBoxTemperatureEntrySoftShutdownValue OBJECT-TYPE
                                 SYNTAX  OCTET STRING
                                 ACCESS  read-only
                                 STATUS  mandatory
                                 DESCRIPTION
                                 "Temperature in degrees centigrade(C).
                                 If the component's temperature rises above this value the
                                 system will be powered off after the O/S is shut down.
                                 If enabled, a critical alert/event is generated.
                                 An octet string expressed as 'sddd.dd Centigrade' where:
                                 s is the sign ('-' for negative or blank space for positive)
                                 d is a decimal digit or blank space for a leading zero.
                                 The string 'Not Readable!' indicates that the given monitor
                                 is not supported on this system."
                                 ::= { expansionBoxTemperatureEntry 6 }

     expansionBoxTemperatureEntryWarningValue OBJECT-TYPE
                                 SYNTAX  OCTET STRING
                                 ACCESS  read-only
                                 STATUS  mandatory
                                 DESCRIPTION
                                 "Temperature in degrees centigrade(C).
                                 If the temperature rises above this value a warning alert/event
                                 if enabled will be generated.
                                 An octet string expressed as 'sddd.dd Centigrade' where:
                                 s is the sign ('-' for negative or blank space for positive)
                                 d is a decimal digit or blank space for a leading zero.
                                 The string 'Not Readable!' indicates that the given monitor
                                 is not supported on this system."
                                 ::= { expansionBoxTemperatureEntry 7 }

     expansionBoxTemperatureEntryWarningResetValue OBJECT-TYPE
                                 SYNTAX  OCTET STRING
                                 ACCESS  read-only
                                 STATUS  mandatory
                                 DESCRIPTION
                                 "Temperature in degrees centigrade(C).
                                 If the temperature rises above this value and
                                 if a warning alert/event had previously been
                                 created then the alert/event will be reset.
                                 An octet string expressed as 'sddd.dd Centigrade' where:
                                 s is the sign ('-' for negative or blank space for positive)
                                 d is a decimal digit or blank space for a leading zero.
                                 The string 'Not Readable!' indicates that the given monitor
                                 is not supported on this system."
                                 ::= { expansionBoxTemperatureEntry 8 }


     -- ***********************************************************************
     -- PCI-X expansion enclosure voltage sensors
     -- ***********************************************************************
     expansionBoxVoltageTable  OBJECT-TYPE
                           SYNTAX  SEQUENCE OF ExpansionBoxVoltageEntry
                           ACCESS  not-accessible
                           STATUS  mandatory
                           DESCRIPTION
                           "Table of voltage sensors for PCI Expansion Box."
                           ::= {  pcixExpansionBox 3 }

     expansionBoxVoltageEntry  OBJECT-TYPE
                           SYNTAX  ExpansionBoxVoltageEntry
                           ACCESS  not-accessible
                           STATUS  mandatory
                           DESCRIPTION
                           "PCI-X expansion enclosure voltage threshold entries."
                           INDEX {pcixExpansionBoxEntryIndex, expansionBoxVoltageEntryIndex }
                           ::= { expansionBoxVoltageTable 1 }

     ExpansionBoxVoltageEntry ::= SEQUENCE {
                  expansionBoxVoltageEntryIndex INTEGER,
                  expansionBoxVoltageEntryName OCTET STRING,
                  expansionBoxVoltageEntryEnclosureSerialNumber OCTET STRING,
                  expansionBoxVoltageEntryCurrentValue OCTET STRING,
                  expansionBoxVoltageThresholdEntryHardShutdownHighValue OCTET STRING,
                  expansionBoxVoltageThresholdEntrySoftShutdownHighValue OCTET STRING,
                  expansionBoxVoltageThresholdEntryWarningHighValue OCTET STRING,
                  expansionBoxVoltageThresholdEntryWarningResetHighValue OCTET STRING,
                  expansionBoxVoltageThresholdEntryHardShutdownLowValue OCTET STRING,
                  expansionBoxVoltageThresholdEntrySoftShutdownLowValue OCTET STRING,
                  expansionBoxVoltageThresholdEntryWarningLowValue OCTET STRING,
                  expansionBoxVoltageThresholdEntryWarningResetLowValue OCTET STRING
      }

     expansionBoxVoltageEntryIndex   OBJECT-TYPE
                                 SYNTAX  INTEGER
                                 ACCESS  read-only
                                 STATUS  mandatory
                                 DESCRIPTION
                                 "PCI-X Expansion voltage sensor index."
                                 ::= { expansionBoxVoltageEntry 1 }

     expansionBoxVoltageEntryName  OBJECT-TYPE
                                 SYNTAX  OCTET STRING
                                 ACCESS  read-only
                                 STATUS  mandatory
                                 DESCRIPTION
                                 "Null terminated string that
                                 contains the power supply's name, for example
                                 'Expansion Enclosure 1 right(A) side +5V'."
                                 ::= { expansionBoxVoltageEntry 2 }

     expansionBoxVoltageEntryEnclosureSerialNumber OBJECT-TYPE
                                 SYNTAX  OCTET STRING
                                 ACCESS  read-only
                                 STATUS  mandatory
                                 DESCRIPTION
                                 "Null terminated string that
                                 contains the individual PCI-X expansion enclosure
                                 serial number."
                                 ::= { expansionBoxVoltageEntry 3 }

     expansionBoxVoltageEntryCurrentValue OBJECT-TYPE
                                 SYNTAX  OCTET STRING
                                 ACCESS  read-only
                                 STATUS  mandatory
                                 DESCRIPTION
                                 "Voltage reading expressed in Volts(V).
                                 An octet string expressed as 'sdd.dd Volts' where:
                                 s is the sign ('-' for negative or '+' for positive)
                                 d is a decimal digit or blank space for a leading zero.
                                 The string 'Not Readable!' indicates that the given monitor
                                 is not supported on this system."
                                 ::= { expansionBoxVoltageEntry 4 }


     expansionBoxVoltageThresholdEntryHardShutdownHighValue OBJECT-TYPE
                                   SYNTAX  OCTET STRING
                                   ACCESS  read-only
                                   STATUS  mandatory
                                   DESCRIPTION
                                   "Voltage threshold reading expressed in Volts(V).
                                   If the voltage rises above this value the
                                   system will be powered off immediately.
                                   If enabled, a critical alert/event will be generated.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 5 }

     expansionBoxVoltageThresholdEntrySoftShutdownHighValue OBJECT-TYPE
                                   SYNTAX  OCTET STRING
                                   ACCESS  read-only
                                   STATUS  mandatory
                                   DESCRIPTION
                                   "Voltage threshold reading expressed in Volts(V).
                                   If the voltage rises above this value the system will be powered off
                                   after the O/S is shut down.
                                   If enabled a critical alert/event is generated.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 6 }

     expansionBoxVoltageThresholdEntryWarningHighValue OBJECT-TYPE
                                   SYNTAX  OCTET STRING
                                   ACCESS  read-only
                                   STATUS  mandatory
                                   DESCRIPTION
                                   "Voltage threshold reading expressed in Volts(V).
                                   If the voltage rises above this value a warning alert/event
                                   if enabled will be generated.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 7 }

     expansionBoxVoltageThresholdEntryWarningResetHighValue OBJECT-TYPE
                                   SYNTAX  OCTET STRING
                                   ACCESS  read-only
                                   STATUS  mandatory
                                   DESCRIPTION
                                   "Voltage threshold reading expressed in Volts(V).
                                   If the voltage rises above this value and
                                   if a warning alert/event had previously been
                                   created then the alert/event will be reset.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 8 }


     expansionBoxVoltageThresholdEntryHardShutdownLowValue OBJECT-TYPE
                                   SYNTAX  OCTET STRING
                                   ACCESS  read-only
                                   STATUS  mandatory
                                   DESCRIPTION
                                   "Voltage threshold reading expressed in Volts(V).
                                   If the voltage drops below this value the
                                   system will be powered off immediately.
                                   If enabled, a critical alert/event will be generated.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 9 }

      expansionBoxVoltageThresholdEntrySoftShutdownLowValue OBJECT-TYPE
                                   SYNTAX  OCTET STRING
                                   ACCESS  read-only
                                   STATUS  mandatory
                                   DESCRIPTION
                                   "Voltage threshold reading expressed in Volts(V).
                                   If the voltage drops below this value the system will be powered off
                                   after the O/S is shut down.
                                   If enabled a critical alert/event is generated.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 10 }

      expansionBoxVoltageThresholdEntryWarningLowValue OBJECT-TYPE
                                   SYNTAX  OCTET STRING
                                   ACCESS  read-only
                                   STATUS  mandatory
                                   DESCRIPTION
                                   "Voltage threshold reading expressed in Volts(V).
                                   If the voltage drops below this value a warning alert/event
                                   if enabled will be generated.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 11 }

      expansionBoxVoltageThresholdEntryWarningResetLowValue OBJECT-TYPE
                                   SYNTAX  OCTET STRING
                                   ACCESS  read-only
                                   STATUS  mandatory
                                   DESCRIPTION
                                   "Voltage threshold reading expressed in Volts(V).
                                   If the voltage drops below this value and
                                   if a warning alert/event had previously been
                                   created then the alert/event will be reset.
                                   An octet string expressed as 'sdd.dd Volts' where:
                                   s is the sign ('-' for negative or '+' for positive)
                                   d is a decimal digit or blank space for a leading zero.
                                   The string 'Not Readable!' indicates that the given monitor
                                   is not supported on this system."
                                   ::= { expansionBoxVoltageEntry 12 }

     -- ***********************************************************************
     -- PCI-X expansion enclosure Fan sensors
     -- ***********************************************************************
     expansionBoxFanTable  OBJECT-TYPE
                           SYNTAX  SEQUENCE OF ExpansionBoxFanEntry
                           ACCESS  not-accessible
                           STATUS  mandatory
                           DESCRIPTION
                           "Table of fan sensors for PCI-X Expansion Box."
                           ::= {  pcixExpansionBox 5 }

     expansionBoxFanEntry  OBJECT-TYPE
                           SYNTAX  ExpansionBoxFanEntry
                           ACCESS  not-accessible
                           STATUS  mandatory
                           DESCRIPTION
                           "PCI-X expansion enclosure fan entries."
                           INDEX {pcixExpansionBoxEntryIndex, expansionBoxFanEntryIndex }
                           ::= { expansionBoxFanTable 1 }

     ExpansionBoxFanEntry ::= SEQUENCE {
                  expansionBoxFanEntryIndex INTEGER,
                  expansionBoxFanEntryName OCTET STRING,
                  expansionBoxFanEntryEnclosureSerialNumber OCTET STRING,
                  expansionBoxFanEntryCurrentValue OCTET STRING
     }

     expansionBoxFanEntryIndex   OBJECT-TYPE
                                 SYNTAX  INTEGER
                                 ACCESS  read-only
                                 STATUS  mandatory
                                 DESCRIPTION
                                 "PCI-X Expansion fan sensor index."
                                 ::= { expansionBoxFanEntry 1 }

     expansionBoxFanEntryName    OBJECT-TYPE
                                 SYNTAX  OCTET STRING
                                 ACCESS  read-only
                                 STATUS  mandatory
                                 DESCRIPTION
                                 "Null terminated string that
                                 contains the fan name, for example
                                 'Expansion Enclosure 1 right(A) side Fan-1'."
                                 ::= { expansionBoxFanEntry 2 }

     expansionBoxFanEntryEnclosureSerialNumber OBJECT-TYPE
                                 SYNTAX  OCTET STRING
                                 ACCESS  read-only
                                 STATUS  mandatory
                                 DESCRIPTION
                                 "Null terminated string that
                                 contains the individual PCI-X expansion enclosure
                                 serial number."
                                 ::= { expansionBoxFanEntry 3 }

     expansionBoxFanEntryCurrentValue OBJECT-TYPE
                                 SYNTAX  OCTET STRING
                                 ACCESS  read-only
                                 STATUS  mandatory
                                 DESCRIPTION
                                 "Fan 1 speed expressed in percent(%) of maximum RPM.
                                 An octet string expressed as 'ddd% of maximum' where:
                                 d is a decimal digit or blank space for a leading zero.
                                 If the fan is determined not to be running or
                                 the fan speed cannot be determined, the string will
                                 indicate 'Offline'.
                                 The string 'Not Readable!' indicates that the given monitor
                                 is not supported on this system."
                                 ::= { expansionBoxFanEntry 4 }

     -- ***********************************************************************
     -- Expansion enclosure VPD
     -- ***********************************************************************
     expansionBoxVpd OBJECT IDENTIFIER ::= {pcixExpansionBox 6}


      -- ***********************************************************************
      -- PCI-X expansion enclosure firmware VPD
      -- ***********************************************************************
      expansionBoxFirmwareVpdTable  OBJECT-TYPE
                            SYNTAX  SEQUENCE OF ExpansionBoxFirmwareVpdEntry
                            ACCESS  not-accessible
                            STATUS  mandatory
                            DESCRIPTION
                            "Table of firmware VPD for PCI-X Expansion Box."
                            ::= {  expansionBoxVpd 1 }

      expansionBoxFirmwareVpdEntry  OBJECT-TYPE
                            SYNTAX  ExpansionBoxFirmwareVpdEntry
                            ACCESS  not-accessible
                            STATUS  mandatory
                            DESCRIPTION
                            "PCI-X expansion enclosure firmware VPD entries."
                            INDEX {pcixExpansionBoxEntryIndex, expansionBoxFirmwareVpdIndex}
                            ::= {expansionBoxFirmwareVpdTable 1 }

      ExpansionBoxFirmwareVpdEntry ::= SEQUENCE {
                   expansionBoxFirmwareVpdIndex INTEGER,
                   expansionBoxFirmwareVpdName OCTET STRING,
                   expansionBoxFirmwareVpdEnclosureSerialNumber OCTET STRING,
                   expansionBoxFirmwareVpdRevisionNumber OCTET STRING
      }

      expansionBoxFirmwareVpdIndex OBJECT-TYPE
                                   SYNTAX  INTEGER
                                   ACCESS  read-only
                                   STATUS  mandatory
                                   DESCRIPTION
                                   "PCI-X Expansion firmware VPD index."
                                   ::= { expansionBoxFirmwareVpdEntry 1 }

      expansionBoxFirmwareVpdName OBJECT-TYPE
                                 SYNTAX  OCTET STRING
                                 ACCESS  read-only
                                 STATUS  mandatory
                                 DESCRIPTION
                                 "Null terminated string that
                                 contains the firmware VPD name for the power
                                 backplane or Integrated Systems Management
                                 Processor (ISMP). For example
                                 'Expansion Enclosure 1 right(A) side ISMP'."
                                 ::= { expansionBoxFirmwareVpdEntry 2 }

      expansionBoxFirmwareVpdEnclosureSerialNumber  OBJECT-TYPE
                                 SYNTAX  OCTET STRING
                                 ACCESS  read-only
                                 STATUS  mandatory
                                 DESCRIPTION
                                 "Null terminated string that
                                 contains the individual PCI-X expansion enclosure
                                 serial number."
                                 ::= { expansionBoxFirmwareVpdEntry 3 }

      expansionBoxFirmwareVpdRevisionNumber   OBJECT-TYPE
                                  SYNTAX  OCTET STRING
                                  ACCESS  read-only
                                  STATUS  mandatory
                                  DESCRIPTION
                                  "PCI-X expansion enclosure power firmware VPD revison
                                  number."
                                  ::= { expansionBoxFirmwareVpdEntry 4 }


END
