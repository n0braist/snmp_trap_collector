WITS-TRAP-MIBv1 DEFINITIONS ::= BEGIN

IMPORTS
   witsCSFamily
      FROM WITS-CSFAMILY-MIB
   TRAP-TYPE
      FROM RFC-1215;

-- trap generic=6 specific=1
witsTraps OBJECT IDENTIFIER ::= { witsCSFamily 2 }

alarmTrap TRAP-TYPE
    ENTERPRISE witsTraps
    DESCRIPTION
            "A generic trap for all alarms. The variable bindings in 
             the trap PDU contain the detailed alarm information."
    -- 1,3,6,1,4,1,1815,1,1,2,1
    ::= 1


END
