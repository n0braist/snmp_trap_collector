SM10-R3-MIB DEFINITIONS ::= BEGIN

-- Initial version. 10/1/98
-- Second turn 10/2/98  added another trap
-- Third version. 10/20/98
-- Fourth version 10/23/98  Changes in this version are
--                                      1) Deleted the FRU code from the MIB
--                                      2) The deviceUserLabel WILL BE the same as the Storage Array Name.
--                                      3) Fixed typos.
--                                      4) The deviceErrorCode WILL BE the same as the MEL event number.
-- The changes came from a meeting held on 10/22/98.
-- Changes to add componentType and componentLocation 08/11/00
--
-- New version of the mib.  The mibs has been renumbered. 10/28/98
-- New version of the mib.  The mib has been renumbered to 204 08/11/00
-- changed symbios to LSI Logic Storage Systems. 05/16/01
-- changed version to 205 7/15/03 SM7_10.MIB
-- SM7_10.MIB reset version back to 204 for this mib. will create a new mib for version 205. new mib is SM8_R4.MIB
-- created SM8_R4.MIB version 205 7/15/03
-- created SM9_R1.MIB version 206 2/12/04 to change the deviceUserLabel from 18 to 30 characters.
-- changed LSI Logic Storage Systems to Engenio Information Technologies changed version to 300. 11/19/2004
-- SM9_R3 replaces SM9_R2.  SM9_R2 has a coding defect. SM9_R3 has been issued to correct this defect. 06/30/2005
-- SM10_R1 introduces support for accommodating both IPv4 and IPv6 IP addresses. 10/25/07
-- SM10-R3 Migrate the private enterprise MIB to NetApp private enterprise tree. 08/02/2011
-- SM10-R3 Changed the length of the deviceUserLabel entry from 29 to 30. 07/03/2012

	IMPORTS
		OBJECT-TYPE,
		MODULE-IDENTITY,
		enterprises,
		NOTIFICATION-TYPE
	FROM SNMPv2-SMI
		DisplayString
      	FROM SNMPv2-TC
		InetAddressType,
		InetAddress
	FROM INET-ADDRESS-MIB
	        OBJECT-GROUP,
	        MODULE-COMPLIANCE,
	        NOTIFICATION-GROUP
	FROM SNMPv2-CONF;

	
	sm10R3 MODULE-IDENTITY
        LAST-UPDATED "201108051503Z" -- August 15, 2011
        ORGANIZATION "NetApp, Inc"
        CONTACT-INFO "http://www.netapp.com/us/support/"
        DESCRIPTION  "SANtricity Storage Manager for E-Series Storage Systems"
        REVISION     "201108051503Z" -- August 15, 2011
        DESCRIPTION  "This is the third revision of the sm10 MIB. This revision of the sm10
                      MIB module has been converted to NetApp private enterprise number space."
        ::= { storageManager 500 }
	      
    
netapp OBJECT IDENTIFIER ::= { enterprises 789 }
--
-- the eSeriesStorageSystem is the NetApp product of E-Series Storage Systems
--
eSeriesStorageSystem   OBJECT IDENTIFIER ::= { netapp 1123 }
--
-- storageManager is host based storage array management software product.
--
storageManager   OBJECT IDENTIFIER ::= { eSeriesStorageSystem 1 }
--
-- sm10R3TrapBase is for "reverse-mappable" between SNMPv1/SNMPv2 conversions.
--
sm10R3TrapBase   OBJECT IDENTIFIER ::= { sm10R3 0 }
--
-- storageServer is SNMP agent embedded in NetApp E-Series storage array or storage controller
--
storageServer    OBJECT IDENTIFIER ::= { eSeriesStorageSystem 2 }

smConformance OBJECT IDENTIFIER ::= { storageManager 8 }

smCompliance  OBJECT IDENTIFIER ::= { smConformance 1 }
smGroups      OBJECT IDENTIFIER ::= { smConformance 2 }

	infoTable OBJECT-TYPE
		 SYNTAX  SEQUENCE OF InfoEntry
		 MAX-ACCESS  not-accessible 
		 STATUS  current
		 DESCRIPTION
		      "Information for array traps."
		 ::= { sm10R3 1 }

	infoEntry OBJECT-TYPE
		 SYNTAX InfoEntry
		 MAX-ACCESS not-accessible
		 STATUS current
		 DESCRIPTION
		     "The data for array traps."
		 INDEX  { deviceHostIPType }
		 ::= { infoTable 1 }     
	
		
	InfoEntry ::= 
	SEQUENCE {
		deviceHostIPType
			InetAddressType,
		deviceHostIPAddr
			InetAddress,
		deviceHostName
			DisplayString,
		deviceUserLabel
			DisplayString,
		deviceErrorCode
			DisplayString,
		eventTime
			DisplayString,
		trapDescription
			DisplayString,
		componentType
			DisplayString,
		componentLocation
			DisplayString
	}			
	deviceHostIPType OBJECT-TYPE
		SYNTAX InetAddressType 
		MAX-ACCESS read-only
		STATUS current
		DESCRIPTION 
			"Type of IP Address of the network-attached device or device host. 0 unknown, 1 ipv4, 2 ipv6"
		::= { infoEntry 1 }
		
	deviceHostIPAddr OBJECT-TYPE
		SYNTAX InetAddress
		MAX-ACCESS read-only
		STATUS current
		DESCRIPTION 
			"IP Address of the network-attached device or device host."
		::= { infoEntry 2 }
				
	deviceHostName OBJECT-TYPE
		SYNTAX DisplayString (SIZE (0..17))
		MAX-ACCESS read-only
		STATUS current
		DESCRIPTION
			"The user label for the host of the device being reported on."
		::= { infoEntry 3 }
		
	deviceUserLabel OBJECT-TYPE
		SYNTAX DisplayString (SIZE (0..30))
		MAX-ACCESS read-only
		STATUS current
		DESCRIPTION
			"The user label for the device being reported on."
		::= { infoEntry 4 }

	deviceErrorCode OBJECT-TYPE
		SYNTAX DisplayString (SIZE (0..19))
		MAX-ACCESS read-only
		STATUS current
		DESCRIPTION
			"The error code as reported by the device or host."
		::= { infoEntry 5 }

	eventTime OBJECT-TYPE
		SYNTAX DisplayString (SIZE (0..39))
		MAX-ACCESS read-only
		STATUS current
		DESCRIPTION 
			"The time at which the event happen on the device."
		::= { infoEntry 6 }

	trapDescription OBJECT-TYPE
		SYNTAX DisplayString (SIZE (0..69))
		MAX-ACCESS read-only
		STATUS current
		DESCRIPTION 
			"A string to indicate the nature of the trap"
		::= { infoEntry 7 }

	componentType OBJECT-TYPE
		SYNTAX DisplayString (SIZE (0..59))
		MAX-ACCESS read-only
		STATUS current
		DESCRIPTION 
			"A string to identify the failing component type"
		::= { infoEntry 8 }

	componentLocation OBJECT-TYPE
		SYNTAX DisplayString (SIZE (0..39))
		MAX-ACCESS read-only
		STATUS current
		DESCRIPTION 
			"A string to identify the location of the failing component"
		::= { infoEntry 9 }

	


--
-- End of items in the info table
--
--      TRAP Definitions
--

storageArrayCritical NOTIFICATION-TYPE
		OBJECTS  { deviceHostIPType, deviceHostIPAddr, deviceHostName, deviceUserLabel, deviceErrorCode, eventTime, trapDescription, componentType, componentLocation }
		STATUS current
		DESCRIPTION
			"This trap indicates an event where user-interaction is required immediately.
			Some example events are component failures or critical errors."
		::= { sm10R3TrapBase 2 }
		

smObjectGroup OBJECT-GROUP
	    OBJECTS { deviceHostIPType, deviceHostIPAddr, deviceHostName,
	              deviceUserLabel, deviceErrorCode, eventTime, 
	              trapDescription, componentType, componentLocation }
	    STATUS  current
	    DESCRIPTION
	            "A collection of objects that are current in this
	            MIB."
    ::= { smGroups 1 }
    

smNotificationGroup NOTIFICATION-GROUP
            NOTIFICATIONS { storageArrayCritical }
            STATUS current
            DESCRIPTION
	    	      "A collection of notifications that are current in this
	    	       MIB."
    ::= { smGroups 2 }
    
smGrpCompliance MODULE-COMPLIANCE
    STATUS  current
    DESCRIPTION
        "The compliance statement for current SNMP entities in
         the NetApp E-Series Storage Systems SM10-R3 MIB."
    MODULE  -- this module
    MANDATORY-GROUPS {
        smObjectGroup,smNotificationGroup
    }
    ::= {smCompliance 1 }	
    
END
