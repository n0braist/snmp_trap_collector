WITS-PRODUCTS-MIB DEFINITIONS ::= BEGIN

IMPORTS
   enterprises,
   MODULE-IDENTITY
      FROM SNMPv2-SMI;

witsRegMIB MODULE-IDENTITY
   LAST-UPDATED "200506081657Z"
   ORGANIZATION "Verint Systems"
   CONTACT-INFO
      "support@witness.com"
   DESCRIPTION
      "The Verint Systems enterprise registration MIB"
   REVISION "200506081657Z"
   DESCRIPTION
      "Initial version."
   ::= { enterprises 1815 }


witsProducts OBJECT IDENTIFIER   ::= { witsRegMIB 1 }

END
