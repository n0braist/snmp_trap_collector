WITS-CSFAMILY-MIB DEFINITIONS ::= BEGIN

IMPORTS
   witsProducts
      FROM WITS-PRODUCTS-MIB
   MODULE-IDENTITY
      FROM SNMPv2-SMI;

witsCSFamily MODULE-IDENTITY
   LAST-UPDATED "200506081704Z"
   ORGANIZATION "Witness Systems"
   CONTACT-INFO
      "support@witness.com"
   DESCRIPTION
      "The ContactStore Family MIB"
   REVISION "200506081704Z"
   DESCRIPTION
      "Initial version."
   ::= { witsProducts 1 }


END
