HP-ICF-OID DEFINITIONS ::= BEGIN

    IMPORTS
        enterprises, MODULE-IDENTITY, OBJECT-IDENTITY
            FROM SNMPv2-SMI;

    icf MODULE-IDENTITY
         LAST-UPDATED "200607271200Z"  -- July 27, 2006
         ORGANIZATION "Hewlett Packard Company,
                       Procurve Networking Business"
         CONTACT-INFO "Hewlett Packard Company
                       8000 Foothills Blvd.
                       Roseville, CA 95747"
         DESCRIPTION  "This MIB module describes devices in the HP 
                      Integrated Communication Facility product 
                      line."

         REVISION     "200609251200Z"  -- Sept 25, 2006 
         DESCRIPTION  "Cleaned up definition of J8715 Chassis."

         REVISION     "200609081200Z"  -- Sept 8, 2006 
         DESCRIPTION  "Added definitions for ESP blades."

         REVISION     "200608221200Z"  -- Aug 22, 2006 
         DESCRIPTION  "Added definitions for hpicfL3MacConfigMIB."

         REVISION     "200608040000Z"  -- August 04, 2006
         DESCRIPTION  "Added definition for hpicfInstMonMIB."

         REVISION     "200607271200Z"  -- July 27, 2006
         DESCRIPTION  "Added definitions for J9032A, J9031A, 
	               J8768A, J8765B, J9033A, J9036A, J9037A, 
		       J8766A and J8988A devices."

         REVISION     "200607260000Z"  -- July 26, 2006
         DESCRIPTION  "Added definition for J9049A and J9050A switch."

         REVISION     "200606300000Z"  -- June 30, 2006
         DESCRIPTION  "Added definition for J9038A device."

         REVISION     "200606051233Z"  -- June 05, 2006
         DESCRIPTION  "Added definition for hpicfDhcpSnoopMIB."

         REVISION     "200605171233Z"  -- May 17, 2006
         DESCRIPTION  "Added definition for hpSwitchAuthorizationMIB."

         REVISION     "200603201627Z" -- Mar. 20, 2006
         DESCRIPTION  "Added definition for J9028A and J9029A switch"

         REVISION     "200601101853Z"  -- Jan.  10, 2006
         DESCRIPTION  "Added definition J8726A device."

         REVISION     "200508041619Z"  -- August 4, 2005
         DESCRIPTION  "Added definitions for hpSwitchAuthenticationMIB,
                      hpSwitchAccountingMIB, hpicfXrrpMIB, hpicfUsrAuthMIB,
                      hpicfPimMIB, hpicfMstpMIB, hpicfUdpFwd,
                      hpicfConnectionRateFilter, hpicfDot1xMIB,
                      hpicfLldpMIB, hpicfVrrpMIB."

         REVISION     "200506081244Z"  -- June 8, 2005
         DESCRIPTION  "Added definition for hpicFrabric."

         REVISION     "200505202123Z"  -- May  20, 2005
         DESCRIPTION  "Added definitions J9001 and J9003 devices."

         REVISION     "200503221926Z"  -- March  22, 2005
         DESCRIPTION  "Added definitions J8771A and J8772A devices."

         REVISION     "200503081530Z"  -- March  08, 2005
         DESCRIPTION  "Added definition for hpSwitchModuleJ8762A,
                      hpSwitch2600n8PPortSlot, updated definition 
                      for J8474A, updated hpSwitchJ8433A,
                      updated hpSwitchJ8474A, and updated 
                      hpSwitchModuleJ8433A."

         REVISION     "200502250041Z"  -- February 24, 2005
         DESCRIPTION  "Added definitions for hpicfRateLimitMIB and
                       J8680A router."

         REVISION     "200501111745Z"  -- January 11, 2005
         DESCRIPTION  "Added definitions for J8770A, J8773A, J8765A,
                       J8764A, J8776A, and J8763A products."

         REVISION     "200501102043Z"  -- January 10, 2005
         DESCRIPTION  "Added definitions for J8697A, J8698A products."

         REVISION     "200409102043Z"  -- September 10, 2004
         DESCRIPTION  "Added definitions for more WAN products."

         REVISION     "200409021030Z"  -- September 02, 2004
         DESCRIPTION  "Added definitions for hpSwitchModuleJ4905A, 
                       hpSwitchModuleJ4906A, hpSwitchModuleJ8433A, 
                       hpSwitchModuleJ8474A, and hpicfJumboMIB."
         
         REVISION     "200408091030Z"  -- August 09, 2004
         DESCRIPTION  "Added ProCurve 6400cl-6XG and 6410cl-6XG."
         
         REVISION     "200407282043Z"  -- July 28, 2004
         DESCRIPTION  "Added definitions for J8718A and J8719A."

         REVISION     "200403310050Z"  -- March 31, 2004
         DESCRIPTION  "Added definitions for 10Gig SR, LR, and ER."


         REVISION     "200403310050Z"  -- March 31, 2004
         DESCRIPTION  "Added ProCurve 2650-CR and 2626-CR Switch 
                       definitions."

         REVISION     "200402122115Z"  -- February 12, 2004
         DESCRIPTION  "Added definition for 10Gig CX4, 
                       ESP port and WAN Products"
	 
         REVISION     "200401201855Z"  -- January 20, 2004
         DESCRIPTION  "Added definitions for J8161A, J4907A, J8162A,
                       J4820B, J4821B, and J4878B."

         REVISION     "200312291705Z"  -- December 29, 2003
         DESCRIPTION  "Added definitions for J4905A and J4906A Switch 
                       definitions."

         REVISION     "200306091617Z"  -- June 9, 2003
         DESCRIPTION  "Added definitions for wireless products."

         REVISION     "200304101118Z"  -- April 10, 2003
         DESCRIPTION  "Added ProCurve 2650-PWR and 2626-PWR Switch 
                       definitions."

	      REVISION     "200302041716Z"  -- February 04, 2003
         DESCRIPTION  "Added  Transceiver cards for HP Switch 2824."

         REVISION     "200301281510Z"  -- January 28, 2003
         DESCRIPTION  "Added ProCurve 2626 Switch definitions."

         REVISION     "200301211633Z"  -- January 21, 2003
         DESCRIPTION  "Added Proliant Switch Object to hpEtherSwitch."

         REVISION     "200204060100Z"  -- April 5, 2002
         DESCRIPTION  "Added new Procurve Switch definitions"

         REVISION     "200011032225Z"  -- November 3, 2000
         DESCRIPTION  "Added new Procurve Switch definitions"

         REVISION     "9909030004Z"  -- September 3, 1999
         DESCRIPTION  "Added definition for ProCurve Routing 
                      Switch products."

         REVISION     "9809240004Z"  -- September 24, 1998
         DESCRIPTION  "Added definitions for 100Mbit and 10/100
                      hub products, and definitions for the
                      ProCurve switch products."

         REVISION     "9710210242Z"  -- October 21, 1997
         DESCRIPTION  "Added definitions for new hub products
                      (10Base-T Hub-12M, 10Base-T Hub-24M, and
                      10Base-T Hub-16M) and Switch 2000 ATM module.
                      Added branch for the Fault Finder MIB."

         REVISION     "9703060342Z"  -- March 6, 1997
         DESCRIPTION  "Added definitions for new switch products
                      (208/224), 100T hub (J3233A).  Added missing
                      include of OBJECT-IDENTITY."

         REVISION     "9609132303Z"  -- September 13, 1996
         DESCRIPTION  "Initial revision.  Split from the former
                      monolithic hpicf MIB."
         ::= { nm 14 }

    hp                OBJECT IDENTIFIER ::= { enterprises 11 }
    nm                OBJECT IDENTIFIER ::= { hp 2 }

    -- Branches under the icf node.  Most of these
    -- branches are defined in other modules.

    icfCommon         OBJECT IDENTIFIER ::= { icf 1 }
    icfHub            OBJECT IDENTIFIER ::= { icf 2 }
    icfBridge         OBJECT IDENTIFIER ::= { icf 3 }

    icfSecurity       OBJECT IDENTIFIER ::= { icf 4 }
    icfConfig         OBJECT IDENTIFIER ::= { icf 5 }

    icfEsSwitch       OBJECT IDENTIFIER ::= { icf 6 }
    hpEs              OBJECT IDENTIFIER ::= { icfEsSwitch 1 }
    hpEs2             OBJECT IDENTIFIER ::= { icfEsSwitch 2 }
    hpNetSwitch       OBJECT IDENTIFIER ::= { icfEsSwitch 3 }

    icfRouter         OBJECT IDENTIFIER ::= { icf 7 }

    icfDot12Draft     OBJECT IDENTIFIER ::= { icf 8 }
    icfVgRepeater     OBJECT IDENTIFIER ::= { icfDot12Draft 1 }
    icfVgInterface    OBJECT IDENTIFIER ::= { icfDot12Draft 2 }

    hpEntityMIB       OBJECT IDENTIFIER ::= { icf 9 }

    hpicfAdmin        OBJECT IDENTIFIER ::= { icf 10 }
    hpicfObjects      OBJECT IDENTIFIER ::= { icf 11 }
    hpicfNotifications OBJECT IDENTIFIER ::= { icf 12 }

    hpicfOEMs         OBJECT IDENTIFIER ::= { icf 13 }
    hpicfFEHub        OBJECT IDENTIFIER ::= { hpicfOEMs 1 }


    -- HP defined transport domains

    hpicfDomains      OBJECT IDENTIFIER ::= { hpicfAdmin 1 }

    hpicfLLCDomain OBJECT-IDENTITY
        STATUS      current
        DESCRIPTION "The SNMP over 802.2 transport domain."
        ::= { hpicfDomains 1 }


    -- Placeholder for registering object modules.  Note that the
    -- MODULE-IDENTITY, MODULE-COMPLIANCE, and OBJECT-GROUP
    -- definitions for each module are declared beneath these
    -- branches.

    hpicfObjectModules OBJECT IDENTIFIER ::= { hpicfAdmin 2 }

    icfSecurityMib    OBJECT IDENTIFIER ::= { hpicfObjectModules 1 }
    hpicfChainMib     OBJECT IDENTIFIER ::= { hpicfObjectModules 2 }
    hpicfChassisMib   OBJECT IDENTIFIER ::= { hpicfObjectModules 3 }
    hpicfDownloadMib  OBJECT IDENTIFIER ::= { hpicfObjectModules 4 }
    hpicfBasicMib     OBJECT IDENTIFIER ::= { hpicfObjectModules 5 }
    hpicfStackMib     OBJECT IDENTIFIER ::= { hpicfObjectModules 6 }
    hpicfLinkTestMib  OBJECT IDENTIFIER ::= { hpicfObjectModules 7 }
    hpicfGenRptrMib   OBJECT IDENTIFIER ::= { hpicfObjectModules 8 }
    hpicf8023RptrMib  OBJECT IDENTIFIER ::= { hpicfObjectModules 9 }
    icfVgRepeaterMib  OBJECT IDENTIFIER ::= { hpicfObjectModules 10 }
    hpicfVgRptrMib    OBJECT IDENTIFIER ::= { hpicfObjectModules 11 }
    hpicfFaultFinderMib OBJECT IDENTIFIER ::= { hpicfObjectModules 12 }
    hpicfJumboMIB OBJECT IDENTIFIER ::= { hpicfObjectModules 13 }
    hpicfRateLimitMIB OBJECT IDENTIFIER ::= { hpicfObjectModules 14 }

    -- Placeholder for registering agent capabilities modules

    hpicfAgentModules OBJECT IDENTIFIER ::= { hpicfAdmin 3 }


       -- Placeholders for branches allocated to agent capabilities
       -- modules

   hpicfETwistHubAgentsMib    OBJECT IDENTIFIER ::= { hpicfAgentModules 1 }
   hpicfETwistBridgeAgentsMib OBJECT IDENTIFIER ::= { hpicfAgentModules 2 }
   hpicfAdvStk8023AgentsMib   OBJECT IDENTIFIER ::= { hpicfAgentModules 3 }
   hpicfAdvStkVGAgentsMib     OBJECT IDENTIFIER ::= { hpicfAgentModules 4 }

   -- Placeholder for the HP ICF Textual Conventions module

   hpicfTextualConventions    OBJECT IDENTIFIER ::= { hpicfAdmin 4 }


    -- Placeholders for branches allocated to other MIB modules
    -- under the hpicfObjects node

    hpicfCommon       OBJECT IDENTIFIER ::= { hpicfObjects 1 }
    hpicfRepeater     OBJECT IDENTIFIER ::= { hpicfObjects 2 }
    hpicfVg           OBJECT IDENTIFIER ::= { hpicfObjects 3 }
    hpicfGenericRepeater OBJECT IDENTIFIER ::= { hpicfObjects 4 }
    hpicfSwitch       OBJECT IDENTIFIER ::= { hpicfObjects 5 }
    hpicfAccess       OBJECT IDENTIFIER ::= { hpicfObjects 6 }
    hpicfWAN          OBJECT IDENTIFIER ::= { hpicfObjects 7 }
    hpicfFabric       OBJECT IDENTIFIER ::= { hpicfObjects 8 }

    -- Branches under the hpicfSwitch node
    hpSwitch          OBJECT IDENTIFIER ::= { hpicfSwitch 1 }

    -- Branches under the hpSwitch node
    hpOpSystem                OBJECT IDENTIFIER ::= { hpSwitch 1 }
    hpHwSystem                OBJECT IDENTIFIER ::= { hpSwitch 2 }
    hpVLAN                    OBJECT IDENTIFIER ::= { hpSwitch 3 }
    hpConfig                  OBJECT IDENTIFIER ::= { hpSwitch 7 }
    hpSwitchStatistics        OBJECT IDENTIFIER ::= { hpSwitch 9 }
    hpSwitchVirtualStackMib   OBJECT IDENTIFIER ::= { hpSwitch 10 }
    hpicfDhcpRelay            OBJECT IDENTIFIER ::= { hpSwitch 11 }
    hpicfBridge               OBJECT IDENTIFIER ::= { hpSwitch 12 }
    hpicfRip                  OBJECT IDENTIFIER ::= { hpSwitch 13 }
    hpicfOspf                 OBJECT IDENTIFIER ::= { hpSwitch 14 }
    hpicfIpRouting            OBJECT IDENTIFIER ::= { hpSwitch 15 }
    hpSwitchAuthenticationMIB OBJECT IDENTIFIER ::= { hpSwitch 16 }
    hpSwitchAccountingMIB     OBJECT IDENTIFIER ::= { hpSwitch 17 }
    hpicfXrrpMIB              OBJECT IDENTIFIER ::= { hpSwitch 18 }
    hpicfUsrAuthMIB           OBJECT IDENTIFIER ::= { hpSwitch 19 }
    hpicfPimMIB               OBJECT IDENTIFIER ::= { hpSwitch 20 }
    hpicfMstpMIB              OBJECT IDENTIFIER ::= { hpSwitch 21 }
    hpicfUdpFwd               OBJECT IDENTIFIER ::= { hpSwitch 23 }
    hpicfConnectionRateFilter OBJECT IDENTIFIER ::= { hpSwitch 24 }
    hpicfDot1xMIB             OBJECT IDENTIFIER ::= { hpSwitch 25 }
    hpicfLldpMIB              OBJECT IDENTIFIER ::= { hpSwitch 30 }
    hpicfVrrpMIB              OBJECT IDENTIFIER ::= { hpSwitch 31 }
    hpSwitchAuthorizationMIB  OBJECT IDENTIFIER ::= { hpSwitch 32 }
    hpicfIpDhcpSnoop          OBJECT IDENTIFIER ::= { hpSwitch 34 }
    hpicfInstMonMIB           OBJECT IDENTIFIER ::= { hpSwitch 35 }
    hpicfL3MacConfigMIB       OBJECT IDENTIFIER ::= { hpSwitch 36 }
    hpicfArpProtect           OBJECT IDENTIFIER ::= { hpSwitch 37 }


    -- Branches under the hpicfCommon node
    hpicfChain        OBJECT IDENTIFIER ::= { hpicfCommon 1 }
    hpicfChassis      OBJECT IDENTIFIER ::= { hpicfCommon 2 }
    hpicfDownload     OBJECT IDENTIFIER ::= { hpicfCommon 3 }
    hpicfBasic        OBJECT IDENTIFIER ::= { hpicfCommon 4 }
    hpicfStack        OBJECT IDENTIFIER ::= { hpicfCommon 5 }
    hpicfLinktest     OBJECT IDENTIFIER ::= { hpicfCommon 6 }
    hpicfFaultFinder  OBJECT IDENTIFIER ::= { hpicfCommon 7 }


    -- Branches for registering HP ICF notifications

    hpicfCommonTraps  OBJECT IDENTIFIER ::= { hpicfNotifications 1 }
    hpicfCommonTrapsPrefix OBJECT IDENTIFIER ::= { hpicfCommonTraps 0 }

    hpicf8023RptrTraps
                         OBJECT IDENTIFIER ::= { hpicfNotifications 2 }
    hpicf8023RptrTrapsPrefix OBJECT IDENTIFIER ::= { hpicf8023RptrTraps 0 }

    hpicfVgRptrTraps  OBJECT IDENTIFIER ::= { hpicfNotifications 3 }
    hpicfVgRptrTrapsPrefix OBJECT IDENTIFIER ::= { hpicfVgRptrTraps 0 }

    hpicfGenRptrTraps OBJECT IDENTIFIER ::= { hpicfNotifications 4 }
    hpicfGenRptrTrapsPrefix OBJECT IDENTIFIER ::= { hpicfGenRptrTraps 0 }

    hpicfRateLimitTraps OBJECT IDENTIFIER ::= { hpicfNotifications 5 }
    hpicfRateLimitTrapsPrefix OBJECT IDENTIFIER ::= { hpicfRateLimitTraps 0 }

    -- HP ICF Device Identifiers

    hpSystem          OBJECT IDENTIFIER ::= { nm 3 }
    netElement        OBJECT IDENTIFIER ::= { hpSystem 7 }


    -- Bridges

    bridge            OBJECT IDENTIFIER ::= { netElement 1 }

    bridge1010 OBJECT-IDENTITY
        STATUS      current
        DESCRIPTION "The authoritative identifier for the 
                    HP 28673A 10:10 LAN Bridge."
        ::= { bridge 1 }

    bridgeRemote OBJECT-IDENTITY
        STATUS      current
        DESCRIPTION "The authoritative identifier for the
                    HP 28674A/B Remote Bridge."
        ::= { bridge 2 }

    eswitch OBJECT-IDENTITY
        STATUS      current
        DESCRIPTION "The authoritative identifier for the
                    HP J2418A EtherTwist LAN Switch."
        ::= { bridge 3 }

    eswitch2 OBJECT-IDENTITY
        STATUS      current
        DESCRIPTION "The authoritative identifier for the
                    HP J2980A AdvanceStack LAN Switch-16."
        ::= { bridge 8 }

    netSwitch100 OBJECT-IDENTITY
        STATUS      current
        DESCRIPTION "The authoritative identifier for the
                    HP J3126A AdvanceStack Switch 100."
        ::= { bridge 9 }

    netSwitch200 OBJECT-IDENTITY
        STATUS      current
        DESCRIPTION "The authoritative identifier for the
                    HP J3125A AdvanceStack Switch 200."
        ::= { bridge 10 }


    -- Routers

    router            OBJECT IDENTIFIER ::= { netElement 2 }

    icfRouterER OBJECT-IDENTITY
        STATUS      current
        DESCRIPTION "The authoritative identifier for the
                    HP 27285A Router ER."
        ::= { router 1 }

    icfRouterTR OBJECT-IDENTITY
        STATUS      current
        DESCRIPTION "The authoritative identifier for the
                    HP 27286A Router TR."
        ::= { router 2 }

    icfRouterSR OBJECT-IDENTITY
        STATUS      current
        DESCRIPTION "The authoritative identifier for the
                    HP 27288A Router SR."
        ::= { router 3 }

    icfRouterFR OBJECT-IDENTITY
        STATUS      current
        DESCRIPTION "The authoritative identifier for the
                    HP 27289A Router FR."
        ::= { router 4 }

    icfRouterLR OBJECT-IDENTITY
        STATUS      current
        DESCRIPTION "The authoritative identifier for the
                    HP Router LR."
        ::= { router 5 }

    icfRouterBR OBJECT-IDENTITY
        STATUS      current
        DESCRIPTION "The authoritative identifier for the
                    HP 27290A Router BR."
        ::= { router 6 }

    icfRouterPR OBJECT-IDENTITY
        STATUS      current
        DESCRIPTION "The authoritative identifier for the
                    HP J2540A Router PR."
        ::= { router 7 }

    icfRouter650 OBJECT-IDENTITY
        STATUS      current
        DESCRIPTION "The authoritative identifier for the
                    HP J2430A AdvanceStack Router 650."
        ::= { router 8 }

    icfRouter230 OBJECT-IDENTITY
        STATUS      current
        DESCRIPTION "The authoritative identifier for the
                    HP J2540B Router 230."
        ::= { router 9 }

    icfRouter250 OBJECT-IDENTITY
        STATUS      current
        DESCRIPTION "The authoritative identifier for the
                    HP 27289B Router 250."
        ::= { router 10 }

    icfRouter255 OBJECT-IDENTITY
        STATUS      current
        DESCRIPTION "The authoritative identifier for the
                    HP J2543A Router 255."
        ::= { router 11 }

    icfRouter210 OBJECT-IDENTITY
        STATUS      current
        DESCRIPTION "The authoritative identifier for the
                    HP J2628A AdvanceStack Router 210."
        ::= { router 12 }

    -- Cards for the Router 650

    icfRouter650Engine OBJECT-IDENTITY
        STATUS      current
        DESCRIPTION "The authoritative identifier for the routing
                    engine card for the HP J2430A AdvanceStack
                    Router 650."
        ::= { icfRouter650 2 }

    icfRouter650Port4E OBJECT-IDENTITY
        STATUS      current
        DESCRIPTION "The authoritative identifier for the
                    HP J2435A AdvanceStack Router 4E Port Module."
        ::= { icfRouter650 3 }

    icfRouter650Port4S OBJECT-IDENTITY
        STATUS      current
        DESCRIPTION "The authoritative identifier for the
                    HP J2434A AdvanceStack Router 4S Port Module."
        ::= { icfRouter650 4 }

    icfRouter650Port4T OBJECT-IDENTITY
        STATUS      current
        DESCRIPTION "The authoritative identifier for the
                    HP J2437A AdvanceStack Router 4T Port Module."
        ::= { icfRouter650 5 }

    icfRouter650PortFDDI OBJECT-IDENTITY
        STATUS      current
        DESCRIPTION "The authoritative identifier for the
                    HP J2436A AdvanceStack Router FDDI Port Module."
        ::= { icfRouter650 6 }

    icfRouter650Port100VG OBJECT-IDENTITY
        STATUS      current
        DESCRIPTION "The authoritative identifier for the
                    HP J2438A AdvanceStack Router 100VG Port
                    Module."
        ::= { icfRouter650 7 }


    -- Hubs

    hub               OBJECT IDENTIFIER ::= { netElement 5 }

    etherTwist12 OBJECT-IDENTITY
        STATUS      current
        DESCRIPTION "The authoritative identifier for the
                    HP 27288A/B EtherTwist Hub PLUS."
        ::= { hub 1 }

    fiberOptic OBJECT-IDENTITY
        STATUS      current
        DESCRIPTION "The authoritative identifier for the
                    HP 28682A Fiber-Optic Hub PLUS."
        ::= { hub 3 }

    etherTwist48 OBJECT-IDENTITY
        STATUS      current
        DESCRIPTION "The authoritative identifier for the
                    HP 28699A EtherTwist Hub PLUS/48."
        ::= { hub 4 }

    thinLAN OBJECT-IDENTITY
        STATUS      current
        DESCRIPTION "The authoritative identifier for the
                    HP 28692A ThinLAN Hub PLUS."
        ::= { hub 5 }

    etherTwist24S OBJECT-IDENTITY
        STATUS      current
        DESCRIPTION "The authoritative identifier for the
                    HP J2355A EtherTwist Secure Hub PLUS/24S"
        ::= { hub 6 }

    advStack12 OBJECT-IDENTITY
        STATUS      current
        DESCRIPTION "The authoritative identifier for the
                    HP J2600A AdvanceStack 10Base-T Hub-12"
        ::= { hub 7 }

    advStack24 OBJECT-IDENTITY
        STATUS      current
        DESCRIPTION "The authoritative identifier for the
                    HP J2601A/B AdvanceStack 10Base-T Hub-24."
        ::= { hub 8 }

    advStack48 OBJECT-IDENTITY
        STATUS      current
        DESCRIPTION "The authoritative identifier for the
                    HP J2602A/B AdvanceStack 10Base-T Hub-48."
        ::= { hub 9 }

    advStackVg15 OBJECT-IDENTITY
        STATUS      current
        DESCRIPTION "The authoritative identifier for the
                    HP J2410A AdvanceStack 100VG Hub-15."
        ::= { hub 10 }

    advStackU8 OBJECT-IDENTITY
        STATUS      current
        DESCRIPTION "The authoritative identifier for the
                    HP J2610A AdvanceStack 10Base-T Hub-8U."
        ::= { hub 11 }

    advStackU16 OBJECT-IDENTITY
        STATUS      current
        DESCRIPTION "The authoritative identifier for the
                    HP J2611A AdvanceStack 10Base-T Hub-16U."
        ::= { hub 12 }

    advStackVg6 OBJECT-IDENTITY
        STATUS      current
        DESCRIPTION "The authoritative identifier for the
                    HP J2413A AdvanceStack 100VG Hub-7M."
        ::= { hub 13 }

    advStackVg12 OBJECT-IDENTITY
        STATUS      current
        DESCRIPTION "The authoritative identifier for the
                    HP J2415A AdvanceStack 100VG Hub-14."
        ::= { hub 14 }

    hpAdvStkEnetSH12R OBJECT-IDENTITY
        STATUS      current
        DESCRIPTION "The authoritative identifier for the
                    HP J3200A AdvanceStack 10BT Switching Hub-12R."
        ::= { hub 15 }

    hpAdvStkEnetSH24R OBJECT-IDENTITY
        STATUS      current
        DESCRIPTION "The authoritative identifier for the
                    HP J3202A AdvanceStack 10BT Switching Hub-24R."
        ::= { hub 16 }

    hpAdvStkEnetSH24T OBJECT-IDENTITY
        STATUS      current
        DESCRIPTION "The authoritative identifier for the
                    HP J3204A AdvanceStack 10BT Switching Hub-24T."
        ::= { hub 17 }

    hpAdvStk100Tx12TM OBJECT-IDENTITY
        STATUS      current
        DESCRIPTION "The authoritative identifier for the
                    HP J3233A AdvanceStack 100B-TX Hub-12TM w/MGMT."
        ::= { hub 18 }

    hp10THub16M OBJECT-IDENTITY
        STATUS      current
        DESCRIPTION "The authoritative identifier for the
                    HP J3188A 10Base-T Hub-16M."
        ::= { hub 19}

    hp10BaseTHub12M OBJECT-IDENTITY
        STATUS      current
        DESCRIPTION "The authoritative identifier for the
                    HP J3301A 10Base-T Hub-12M"
        ::= { hub 20 }

    hp10BaseTHub24M OBJECT-IDENTITY
        STATUS      current
        DESCRIPTION "The authoritative identifier for the
                    HP J3303A 10Base-T Hub-24M"
        ::= { hub 21 }

    hpProCurve10T100THub12M OBJECT-IDENTITY
        STATUS      current
        DESCRIPTION "The authoritative identifier for the
                    HP J3288A ProCurve 100Base-T Hub 12M"
        ::= { hub 22 }

    hpProCurve10T100THub24M OBJECT-IDENTITY
        STATUS      current
        DESCRIPTION "The authoritative identifier for the
                    HP J3289A ProCurve 100Base-T Hub 24M"
        ::= { hub 23 }


    -- Entity MIB OIDs

    chassis           OBJECT IDENTIFIER ::= { netElement 8 }

    repeaterAgent OBJECT-IDENTITY
        STATUS      current
        DESCRIPTION "The authoritative identifier for the
                    HP J2603A/B AdvanceStack Ethernet SNMP module."
        ::= { chassis 1 }


    chassisAgents     OBJECT IDENTIFIER ::= { chassis 2 }

    icfVgAgent OBJECT-IDENTITY
        STATUS      current
        DESCRIPTION "The authoritative identifier for the
                    HP J2414A AdvanceStack 100VG/ET SNMP/Bridge
                    Module."
        ::= { chassisAgents 1 }

    icfVgAgent2 OBJECT-IDENTITY
        STATUS      current
        DESCRIPTION "The authoritative identifier for the
                    HP J2414B AdvanceStack 100VG/ET SNMP/Bridge
                    Module."
        ::= { chassisAgents 3 }

    hpicfEnetSMM OBJECT-IDENTITY
        STATUS      current
        DESCRIPTION "The authoritative identifier for the
                    HPJ3133A AdvanceStack 8U/16U SNMP Module."
        ::= { chassisAgents 4 }

    hpAdvStkEnetSHAgent OBJECT-IDENTITY
        STATUS      current
        DESCRIPTION "The authoritative identifier for the
                    HPJ3210A AdvanceStack 10BT Switching Hub
                    Management Module."
        ::= { chassisAgents 5 }

    hpAdvStkSwStackTopMgmt OBJECT-IDENTITY
        STATUS      current
        DESCRIPTION "The authoritative identifier for the
                    HPJ3179A AdvanceStack Switch StackTop Management
                    Module."
        ::= { chassisAgents 6 }

    hpSwitch8000CpuCard OBJECT-IDENTITY
        STATUS      current
        DESCRIPTION "The authoritative identifier for the
                    HP J4110A Switch 8000M and HP J4121A Switch
                    4000M CPU card."
        ::= { chassisAgents 7 }

    icfSensors        OBJECT IDENTIFIER ::= { chassis 3 }

    icfPowerSupplySensor OBJECT-IDENTITY
        STATUS      current
        DESCRIPTION "Identifier for a power supply sensor type."
        ::= { icfSensors 1 }

    icfFanSensor OBJECT-IDENTITY
        STATUS      current
        DESCRIPTION "Identifier for a fan sensor type."
        ::= { icfSensors 2 }

    icfTemperatureSensor OBJECT-IDENTITY
        STATUS      current
        DESCRIPTION "Identifier for a temperature sensor type."
        ::= { icfSensors 3 }

    icfFutureSlotSensor OBJECT-IDENTITY
        STATUS      current
        DESCRIPTION "Identifier for a FutureSlot sensor type."
        ::= { icfSensors 4 }


    icfCards          OBJECT IDENTIFIER ::= { chassis 4 }

    icfUnidentifiedCard OBJECT-IDENTITY
        STATUS      current
        DESCRIPTION "Used to indicate that a module is installed in
                    a slot in a chassis, but the agent is unable to
                    identify it."
        ::= { icfCards 1 }

    hpAdvStkEnetSHSwitch OBJECT-IDENTITY
        STATUS      current
        DESCRIPTION "The authoritative identifier for the
                    HP J3212A AdvanceStack 10BT Switching Hub Switch
                    Module."
        ::= { icfCards 2 }

    hpAdvStkSwStackExpander OBJECT-IDENTITY
        STATUS      current
        DESCRIPTION "The authoritative identifier for the
                    HPJ3180A AdvanceStack Switch Stack Expander
                    Module."
        ::= { icfCards 3 }

    hpicfStacks       OBJECT IDENTIFIER ::= { chassis 5 }

    hpAdvStkEnetSHStack OBJECT-IDENTITY
        STATUS      current
        DESCRIPTION "The authoritative identifier for a stack of
                    HP AdvanceStack 10Base-T Switching Hubs."
        ::= { hpicfStacks 1 }


    hpicfBackplanes   OBJECT IDENTIFIER ::= { chassis 6 }

    hpAdvStkEnetSHExtSeg OBJECT-IDENTITY
        STATUS      current
        DESCRIPTION "The authoritative identifier for an inter-box
                    repeater segment in a stack of HP AdvanceStack
                    10Base-T Switching Hubs."
        ::= { hpicfBackplanes 1 }

    hpAdvStkEnetSHIntSeg OBJECT-IDENTITY
        STATUS      current
        DESCRIPTION "The authoritative identifier for a repeater
                    segment that is internal to a single box in
                    a stack of HP AdvanceStack 10Base-T Switching
                    Hubs."
        ::= { hpicfBackplanes 2 }

    hp10BaseTHubSeg OBJECT-IDENTITY
        STATUS      current
        DESCRIPTION "The authoritative identifier for a repeater
                    segment in an HP 10Base-T Hub-12M or HP
                    10Base-T Hub-24M."
        ::= { hpicfBackplanes 3 }

    hpSwitchBackplane OBJECT-IDENTITY
        STATUS      current
        DESCRIPTION "The authoritative identifier for an HP Switch
                    backplane."
        ::= { hpicfBackplanes 4 }

    hp100BaseTHubSeg OBJECT-IDENTITY
        STATUS      current
        DESCRIPTION "The authoritative identifier for a repeater
                    segment in an HP ProCurve 100Base-T Hub 12M
                    or HP ProCurve 100Base-T Hub 24M."
        ::= { hpicfBackplanes 5 }



    hpicfSlots        OBJECT IDENTIFIER ::= { chassis 7 }

    hpAdvStkEnetSHAgentSlot OBJECT-IDENTITY
        STATUS      current
        DESCRIPTION "The authoritative identifier for the Management
                    Slot in an HP AdvanceStack 10Base-T Switching
                    Hub."
        ::= { hpicfSlots 1 }

    hpAdvStkEnetSHIOSlot OBJECT-IDENTITY
        STATUS      current
        DESCRIPTION "The authoritative identifier for the Expansion
                    Slot in an HP AdvanceStack 10Base-T Switching
                    Hub."
        ::= { hpicfSlots 2 }

    hpAdvStkSwStackMgmtSlot OBJECT-IDENTITY
        STATUS      current
        DESCRIPTION "The authoritative identifier for the
                    Management/Stacking Slot in an HP AdvanceStack
                    Switch 208 or Switch 224."
        ::= { hpicfSlots 3 }

    hpAdvStkSwStackExpSlot OBJECT-IDENTITY
        STATUS      current
        DESCRIPTION "The authoritative identifier for the
                    Expansion Slot in an HP AdvanceStack Switch 208
                    or Switch 224."
        ::= { hpicfSlots 4 }

    hpSwitch8000PowerSupplyBay OBJECT-IDENTITY
        STATUS      current
        DESCRIPTION "The authoritative identifier for a
                    power supply bay in an HP Switch 8000 or
                    HP Switch 4000."
        ::= { hpicfSlots 5 }

    hpSwitch8000CpuSlot OBJECT-IDENTITY
        STATUS      current
        DESCRIPTION "The authoritative identifier for the CPU
                    slot in an HP Switch 8000 or HP Switch 4000."
        ::= { hpicfSlots 6 }

    hpSwitch8000PortSlot OBJECT-IDENTITY
        STATUS      current
        DESCRIPTION "The authoritative identifier for a port
                    module slot in an HP Switch 8000, HP Switch
                    4000, HP Switch 1600, or HP Switch 2400/2424."
        ::= { hpicfSlots 7 }

    hpSwitch2524PortSlot OBJECT-IDENTITY
        STATUS      current
        DESCRIPTION "The authoritative identifier for a port
                    module slot in an HP Switch 2524, HP Switch
                    2512, or HP Network Blade."
        ::= { hpicfSlots 8 }

    hpSwitch5308PowerSupplyBay OBJECT-IDENTITY
        STATUS      current
        DESCRIPTION "The authoritative identifier for a
                    power supply bay in an HP Switch 5308XL or
                    HP Switch 5304XL."
        ::= { hpicfSlots 9 }

    hpSwitch5308PortSlot OBJECT-IDENTITY
        STATUS      current
        DESCRIPTION "The authoritative identifier for a port
                    module slot in an HP Switch 5308XL, HP Switch
                    5304XL, HP Switch 3324XL, or HP Switch 3124XL."
        ::= { hpicfSlots 10 }

    hpSwitch4865PowerSupplyBay OBJECT-IDENTITY
        STATUS      current
        DESCRIPTION "The authoritative identifier for a
                    power supply bay in an HP Switch 4108GL."
        ::= { hpicfSlots 11 }

    hpSwitch4865PortSlot OBJECT-IDENTITY
        STATUS      current
        DESCRIPTION "The authoritative identifier for a port
                    module slot in an HP Switch 4108GL."
        ::= { hpicfSlots 12 }

    hpSwitch2650PortSlot OBJECT-IDENTITY
        STATUS      current
        DESCRIPTION "The authoritative identifier for a port
                    module slot in an HP Switch 2650."
        ::= { hpicfSlots 13 }

    hpSwitch6108PortSlot OBJECT-IDENTITY
        STATUS      current
        DESCRIPTION "The authoritative identifier for a port
                    module slot in an HP Switch 6108."
        ::= { hpicfSlots 14 }
    
    hpSwitch2824PortSlot OBJECT-IDENTITY
        STATUS      current
        DESCRIPTION "The authoritative identifier for a port
                    module slot in an HP Switch 2824 or HP Switch 2848."
        ::= { hpicfSlots 15 }

    hpSwitch2626PortSlot OBJECT-IDENTITY
        STATUS      current
        DESCRIPTION "The authoritative identifier for a port
                    module slot in an HP Switch 2626."
        ::= { hpicfSlots 16 }

    hpSwitch2650PPortSlot OBJECT-IDENTITY
        STATUS      current
        DESCRIPTION "The authoritative identifier for a port
                    module slot in an HP Switch 2650-PWR."
        ::= { hpicfSlots 17 }

    hpSwitch2626PPortSlot OBJECT-IDENTITY
        STATUS      current
        DESCRIPTION "The authoritative identifier for a port
                    module slot in an HP Switch 2626-PWR."
        ::= { hpicfSlots 18 }

    hpSwitch3324PortSlot OBJECT-IDENTITY
	STATUS      current
	DESCRIPTION "The authoritative identifier for a port
		    module slot in an HP Switch 3400cl-24G or 
		    HP Switch 3400cl-48G."
        ::= { hpicfSlots 19 }

    hpSwitch2650CRPortSlot OBJECT-IDENTITY
        STATUS      current
        DESCRIPTION "The authoritative identifier for a port
                    module slot in an HP Switch 2650-CR."
        ::= { hpicfSlots 20 }

    hpSwitch2626CRPortSlot OBJECT-IDENTITY
        STATUS      current
        DESCRIPTION "The authoritative identifier for a port
                    module slot in an HP Switch 2626-CR."
        ::= { hpicfSlots 21 }

    hpSwitch2600n8PPortSlot OBJECT-IDENTITY
        STATUS      current
        DESCRIPTION "The authoritative identifier for a port
                    module slot in an HP Switch 2600-8-PWR."
        ::= { hpicfSlots 22 }

    hpSwitch869xPowerSupplyBay OBJECT-IDENTITY
        STATUS      current
        DESCRIPTION "The authoritative identifier for a
                    power supply bay in an HP Switch 8697 or
                    HP Switch 8698."
        ::= { hpicfSlots 23 }

    hpSwitch869xPortSlot OBJECT-IDENTITY
        STATUS      current
        DESCRIPTION "The authoritative identifier for a port
                    module slot in an HP Switch 8697, HP Switch 8698,
                    HP Switch 8692, HP switch 8693 and HP Switch 8992."
        ::= { hpicfSlots 24 }

    hpSwitch2510PortSlot OBJECT-IDENTITY
        STATUS      current
        DESCRIPTION "The authoritative identifier for a port
                    module slot in an HP Switch 2510vl-24 or
                    HP Switch 2510vl-48."
        ::= { hpicfSlots 25 }

    hpSwitch2810PortSlot OBJECT-IDENTITY
        STATUS      current
        DESCRIPTION "The authoritative identifier for a port
                    module slot in an HP Switch 2810vl-24G or
                    HP Switch 2810vl-48G."
        ::= { hpicfSlots 26 }

    hpSwitch5400CpuCardBay OBJECT-IDENTITY
        STATUS      current
        DESCRIPTION "The authoritative identifier for a
                    Management Module bay in a Procurve Switch 54XXZL or
                    Procurve Switch 8212ZL."
        ::= { hpicfSlots 27 }

    hpSwitch8212FabricBay OBJECT-IDENTITY
        STATUS      current
        DESCRIPTION "The authoritative identifier for a
                    Fabric bay in a Procurve Switch 8212ZL."
        ::= { hpicfSlots 28 }

    hpicfHubPorts     OBJECT IDENTIFIER ::= { chassis 8 }

    hpAdvStkEnetSHExtPort OBJECT-IDENTITY
        STATUS      current
        DESCRIPTION "The authoritative identifier for a repeater
                     port which has an external connector on an HP
                    AdvanceStack 10Base-T Switching Hub."
        ::= { hpicfHubPorts 1 }

    hpAdvStkEnetSHIntPort OBJECT-IDENTITY
        STATUS      current
        DESCRIPTION "The authoritative identifier for a repeater
                    port which does not have an external connector
                    on an HP AdvanceStack 10Base-T Switching Hub.
                    This port may be used to connect to an interface
                    on an expansion module."
        ::= { hpicfHubPorts 2 }

    hpAdvStkEnetSHAgentPort OBJECT-IDENTITY
        STATUS      current
        DESCRIPTION "The authoritative identifier for an internal
                    repeater port used to connect to an interface on
                    a management module in an HP AdvanceStack
                    10Base-T Switching Hub."
        ::= { hpicfHubPorts 3 }

    hp10BaseTHubPort OBJECT-IDENTITY
        STATUS      current
        DESCRIPTION "The authoritative identifier for a repeater
                    port which has an external connector on an HP
                    10Base-T Hub-12M or an HP 10Base-T Hub-24M."
        ::= { hpicfHubPorts 4 }

    hp10BaseTHubAgentPort OBJECT-IDENTITY
        STATUS      current
        DESCRIPTION "The authoritative identifier for an internal
                    repeater port used to connect to an agent
                    interface in an HP 10Base-T Hub-12M or an HP
                    10Base-T Hub-24M."
        ::= { hpicfHubPorts 5 }

    hp10T100THubPort OBJECT-IDENTITY
        STATUS      current
        DESCRIPTION "The authoritative identifier for a 10/100
                    repeater port that has an external connector
                    on an HP ProCurve 100Base-T Hub."
        ::= { hpicfHubPorts 6 }

    hp100BaseTHubAgentPort OBJECT-IDENTITY
        STATUS      current
        DESCRIPTION "The authoritative identifier for an internal
                    100Mbit repeater port used to connect to an
                    agent interface in an HP ProCurve 100Base-T
                    Hub."
        ::= { hpicfHubPorts 7 }


    hpicfEnetChipSets OBJECT IDENTIFIER ::= { chassis 9 }

    hpicfEnetChipSetHydra OBJECT-IDENTITY
        STATUS      current
        DESCRIPTION "The authoritative identifier for the
                    HP Hydra 4-interface Ethernet LAN controller."
        ::= { hpicfEnetChipSets 1 }

    hpicfEnetChipSetGT48001 OBJECT-IDENTITY
        STATUS      current
        DESCRIPTION "The authoritative identifier for the
                    GT48001 8-interface switch chip."
        ::= { hpicfEnetChipSets 2 }

    hpicfEnetChipSetPentagon OBJECT-IDENTITY
        STATUS      current
        DESCRIPTION "The authoritative identifier for the
                    HP Pentagon ASIC."
        ::= { hpicfEnetChipSets 3 }


    hpicfSwitchPorts  OBJECT IDENTIFIER ::= { chassis 10 }

    hpicfSwitchPort10T100TX OBJECT-IDENTITY
        STATUS      current
        DESCRIPTION "The authoritative identifier for an IEEE
                    802.3 10BASE-T/100BASE-TX autonegotiating port
                    on an HP switch."
        ::= { hpicfSwitchPorts 1 }

    hpicfSwitchPort100FX  OBJECT-IDENTITY
        STATUS      current
        DESCRIPTION "The authoritative identifier for an IEEE
                    802.3 100BASE-FX port on an HP switch."
        ::= { hpicfSwitchPorts 2 }

    hpicfSwitchPort10FL OBJECT-IDENTITY
        STATUS      current
        DESCRIPTION "The authoritative identifier for an IEEE
                    802.3 10BASE-FL port on an HP switch."
        ::= { hpicfSwitchPorts 3 }

    hpicfSwitchPort1000SX OBJECT-IDENTITY
        STATUS      current
        DESCRIPTION "The authoritative identifier for an IEEE
                    802.3 1000BASE-SX port on an HP switch."
        ::= { hpicfSwitchPorts 4 }

    hpicfSwitchPort10T OBJECT-IDENTITY
        STATUS      current
        DESCRIPTION "The authoritative identifier for an IEEE
                    802.3 10BASE-T port on an HP switch."
        ::= { hpicfSwitchPorts 5 }

    hpicfSwitchPort1000LX OBJECT-IDENTITY
        STATUS      current
        DESCRIPTION "The authoritative identifier for an IEEE
                    802.3 1000BASE-LX port on an HP switch."
        ::= { hpicfSwitchPorts 6 }

    hpicfSwitchPort1000T OBJECT-IDENTITY
        STATUS      current
        DESCRIPTION "The authoritative identifier for an IEEE
                    802.3 1000BASE-T port on an HP switch."
        ::= { hpicfSwitchPorts 7 }

    hpicfSwitchPort1000Stk OBJECT-IDENTITY
        STATUS      current
        DESCRIPTION "The authoritative identifier for an IEEE
                    802.3 1000BASE-Stk port on an HP switch."
        ::= { hpicfSwitchPorts 8 }

    hpicfSwitchPort1000LH OBJECT-IDENTITY
        STATUS      current
        DESCRIPTION "The authoritative identifier for an IEEE
                    802.3 1000BASE-LH port on an HP switch."
        ::= { hpicfSwitchPorts 9 }

    hpicfSwitchPort10GigBaseCX4 OBJECT-IDENTITY
        STATUS      current
        DESCRIPTION "The authoritative identifier for an IEEE
                    802.3 10GIGBASE-CX4 port on an HP switch."
        ::= { hpicfSwitchPorts 10 }

    hpicfSwitchPort1000ESP OBJECT-IDENTITY
        STATUS      current
        DESCRIPTION "The authoritative identifier for an internal
                     ESP Blade port on an HP switch."
        ::= { hpicfSwitchPorts 11 }

    hpicfSwitchPort10GigBaseSR OBJECT-IDENTITY
        STATUS      current
        DESCRIPTION "The authoritative identifier for an IEEE
                    802.3 10GIGBASE-SR port on an HP switch."
        ::= { hpicfSwitchPorts 12 }

    hpicfSwitchPort10GigBaseER OBJECT-IDENTITY
        STATUS      current
        DESCRIPTION "The authoritative identifier for an IEEE
                    802.3 10GIGBASE-ER port on an HP switch."
        ::= { hpicfSwitchPorts 13 }

    hpicfSwitchPort10GigBaseLR OBJECT-IDENTITY
        STATUS      current
        DESCRIPTION "The authoritative identifier for an IEEE
                    802.3 10GIGBASE-LR port on an HP switch."
        ::= { hpicfSwitchPorts 14 }
	

    -- Temporary assignments for IEEE 802.3 MAU types.  These are only used
    -- for MAUs that are not yet defined in the standard MAU MIB at the
    -- time products are released.  They are deprecated when the standard
    -- MAU MIB is updated to include a standard identifier for the MAU.
    -- These are also used for proprietary connectors, like stacking
    -- connectors.

    hpicfMAUTypes     OBJECT IDENTIFIER ::= { chassis 11 }

    hpicfMauType1000BaseSXHD OBJECT-IDENTITY
        STATUS      deprecated
        DESCRIPTION "IEEE 802.3 X fiber over short-wavelength
                    laser PMD (clause 38), half-duplex."
        ::= { hpicfMAUTypes 1 }

    hpicfMauType1000BaseSXFD OBJECT-IDENTITY
        STATUS      deprecated
        DESCRIPTION "IEEE 802.3 X fiber over short-wavelength
                    laser PMD (clause 38), full-duplex."
        ::= { hpicfMAUTypes 2 }

    hpicfMauType1000BaseLXHD OBJECT-IDENTITY
        STATUS      deprecated
        DESCRIPTION "IEEE 802.3 X fiber over long-wavelength
                    laser PMD (clause 38), half-duplex."
        ::= { hpicfMAUTypes 3 }

    hpicfMauType1000BaseLXFD OBJECT-IDENTITY
        STATUS      deprecated
        DESCRIPTION "IEEE 802.3 X fiber over long-wavelength
                    laser PMD (clause 38), full-duplex."
        ::= { hpicfMAUTypes 4 }

    hpicfMauType1000BaseTHD OBJECT-IDENTITY
        STATUS      deprecated
        DESCRIPTION "IEEE 802.3 four-pair Category 5 UTP
                    PHY (clause 40), half-duplex."
        ::= { hpicfMAUTypes 5 }

    hpicfMauType1000BaseTFD OBJECT-IDENTITY
        STATUS      deprecated
        DESCRIPTION "IEEE 802.3 four-pair Category 5 UTP
                    PHY (clause 40), full-duplex."
        ::= { hpicfMAUTypes 6 }

    hpicfMauType1000BaseStkHD OBJECT-IDENTITY
        STATUS      current
        DESCRIPTION "IEEE 802.3 X copper, half-duplex."
        ::= { hpicfMAUTypes 7 }

    hpicfMauType1000BaseStkFD OBJECT-IDENTITY
        STATUS      current
        DESCRIPTION "IEEE 802.3 X copper, full-duplex."
        ::= { hpicfMAUTypes 8 }

    hpicfMauType1000BaseLHFD OBJECT-IDENTITY
        STATUS      current
        DESCRIPTION "Proprietary Long Haul, Fiber full-duplex."
        ::= { hpicfMAUTypes 9 }

    hpicfMauType1000BaseEspPCS OBJECT-IDENTITY
        STATUS      current
        DESCRIPTION "Proprietary internal, PCS port."
        ::= { hpicfMAUTypes 10 }

    hpicfMauType1000BaseEspG OBJECT-IDENTITY
        STATUS      current
        DESCRIPTION "Proprietary internal, GMII port."
        ::= { hpicfMAUTypes 11 }
    
    hpicfMauType10GigBaseCX4 OBJECT-IDENTITY
        STATUS      current
        DESCRIPTION "Proprietary 10Gig CX4, full-duplex."
        ::= { hpicfMAUTypes 12 }

    hpicfMauType10GigBaseSR OBJECT-IDENTITY
        STATUS      current
        DESCRIPTION "Proprietary 10Gig SR, full-duplex."
        ::= { hpicfMAUTypes 13 }

    hpicfMauType10GigBaseER OBJECT-IDENTITY
        STATUS      current
        DESCRIPTION "Proprietary 10Gig ER, full-duplex."
        ::= { hpicfMAUTypes 14 }

    hpicfMauType10GigBaseLR OBJECT-IDENTITY
        STATUS      current
        DESCRIPTION "Proprietary 10Gig LR, full-duplex."
        ::= { hpicfMAUTypes 15 }

    -- Ethernet switches

    hpEtherSwitch     OBJECT IDENTIFIER ::= { netElement 11 }

    -- Entity MIB support for older switches

    hpEtherSwitchPortType OBJECT IDENTIFIER ::= { hpEtherSwitch 99 }

    hpEtherSwitchPort10T   OBJECT IDENTIFIER ::= { hpEtherSwitchPortType 1 }
    hpEtherSwitchPort100T  OBJECT IDENTIFIER ::= { hpEtherSwitchPortType 2 }
    hpEtherSwitchPort100VG OBJECT IDENTIFIER ::= { hpEtherSwitchPortType 3 }
    hpEtherSwitchPort100F  OBJECT IDENTIFIER ::= { hpEtherSwitchPortType 4 }

    hpAdvSwitch2000 OBJECT-IDENTITY
        STATUS      current
        DESCRIPTION "The authoritative identifier for the
                    HP J3100A AdvanceStack Switch 2000."
        ::= { hpEtherSwitch 1 }

    hpAdvSwitch2000B OBJECT-IDENTITY
        STATUS      current
        DESCRIPTION "The authoritative identifier for the
                    HP J3100B AdvanceStack Switch 2000B."
        ::= { hpEtherSwitch 2 }

    hpAdvSwitch800T OBJECT-IDENTITY
        STATUS      current
        DESCRIPTION "The authoritative identifier for the
                    HP J3245A AdvanceStack Switch 800T."
        ::= { hpEtherSwitch 3 }

    hpAdvSwitch200   OBJECT-IDENTITY
        STATUS      current
        DESCRIPTION "The authoritative identifier for the
                    HP J3175A AdvanceStack Switch 208T and
                    HP J3177A AdvanceStack Switch 224T."
        ::= { hpEtherSwitch  4 }

    -- Different types of Switch 200s (desktop switches)
    hpAdvSwitch208T       OBJECT IDENTIFIER ::= { hpAdvSwitch200 1 }
    hpAdvSwitch208VG      OBJECT IDENTIFIER ::= { hpAdvSwitch200 2 }
    hpAdvSwitch224T       OBJECT IDENTIFIER ::= { hpAdvSwitch200 3 }
    hpAdvSwitch224VG      OBJECT IDENTIFIER ::= { hpAdvSwitch200 4 }


    hpSwitch212M OBJECT-IDENTITY
        STATUS      current
        DESCRIPTION "The authoritative identifier for the
                    HP J3298A Switch 212M."
        ::= { hpEtherSwitch 5 }

    hpSwitch224M OBJECT-IDENTITY
        STATUS      current
        DESCRIPTION "The authoritative identifier for the
                    HP J3299A Switch 224M."
        ::= { hpEtherSwitch 6 }

    hpSwitch8000 OBJECT-IDENTITY
        STATUS      current
        DESCRIPTION "The authoritative identifier for the
                    HP J4110A Switch 8000M."
        ::= { hpEtherSwitch 7 }

    hpSwitch1600 OBJECT-IDENTITY
        STATUS      current
        DESCRIPTION "The authoritative identifier for the
                    HP J4120A Switch 1600M."
        ::= { hpEtherSwitch 8 }

    hpSwitch4000 OBJECT-IDENTITY
        STATUS      current
        DESCRIPTION "The authoritative identifier for the
                    HP J4121A Switch 4000M."
        ::= { hpEtherSwitch 9 }

    hpSwitch2400 OBJECT-IDENTITY
        STATUS      current
        DESCRIPTION "The authoritative identifier for the
                    HP J4122A Switch 2400M."
        ::= { hpEtherSwitch 10 }

    hpSwitch2424 OBJECT-IDENTITY
        STATUS      current
        DESCRIPTION "The authoritative identifier for the
                    HP J4122B Switch 2424M."
        ::= { hpEtherSwitch 11 }

    hpSwitch9308 OBJECT-IDENTITY
        STATUS      current
        DESCRIPTION "The authoritative identifier for the
                    HP J4138A Routing Switch 9308M."
        ::= { hpEtherSwitch 13 }

    hpSwitch9304 OBJECT-IDENTITY
        STATUS      current
        DESCRIPTION "The authoritative identifier for the
                    HP J4139A Routing Switch 9304M."
        ::= { hpEtherSwitch 14 }

    hpSwitch6308 OBJECT-IDENTITY
        STATUS      current
        DESCRIPTION "The authoritative identifier for the
                    HP J4840A Routing Switch 6308M."
        ::= { hpEtherSwitch 15 }

    hpSwitch6208 OBJECT-IDENTITY
        STATUS      current
        DESCRIPTION "The authoritative identifier for the
                    HP J4841A Switch 6208M."
        ::= { hpEtherSwitch 16 }

    hpSwitchJ4819A OBJECT-IDENTITY
        STATUS      current
        DESCRIPTION "The authoritative identifier for the
                    HP J4819A Switch 5308XL."
        ::= { hpEtherSwitch 17 }

    hpSwitchJ4812A OBJECT-IDENTITY
        STATUS      current
        DESCRIPTION "The authoritative identifier for the
                    HP J4812A Switch 2512."
        ::= { hpEtherSwitch 18 }

    hpSwitchJ4813A OBJECT-IDENTITY
        STATUS      current
        DESCRIPTION "The authoritative identifier for the
                    HP J4813A Switch 2524."
        ::= { hpEtherSwitch 19 }

    hpSwitchJ4850A OBJECT-IDENTITY
        STATUS      current
        DESCRIPTION "The authoritative identifier for the
                    HP J4819A Switch 5304XL."
        ::= { hpEtherSwitch 20 }

    hpSwitchJ4815A OBJECT-IDENTITY
        STATUS      current
        DESCRIPTION "The authoritative identifier for the
                    HP J4819A Switch 3324XL."
        ::= { hpEtherSwitch 21 }

    hpSwitchJ4851A OBJECT-IDENTITY
        STATUS      current
        DESCRIPTION "The authoritative identifier for the
                    HP J4819A Switch 3124."
        ::= { hpEtherSwitch 22 }

    hpSwitchJ4865A OBJECT-IDENTITY
        STATUS      current
        DESCRIPTION "The authoritative identifier for the
                    HP J4865A Switch 4108GL."
        ::= { hpEtherSwitch 23 }

    hpSwitchA6713A OBJECT-IDENTITY
        STATUS      current
        DESCRIPTION "The authoritative identifier for the
                    HP A6713A Network Blade."
        ::= { hpEtherSwitch 24 }

    hpSwitchA6716A OBJECT-IDENTITY
        STATUS      current
        DESCRIPTION "The authoritative identifier for the
                    HP A6716A Network Blade."
        ::= { hpEtherSwitch 25 }

    hpSwitchA6717A OBJECT-IDENTITY
        STATUS      current
        DESCRIPTION "The authoritative identifier for the
                    HP A6717A Network Blade."
        ::= { hpEtherSwitch 26 }

    hpSwitchJ4887A OBJECT-IDENTITY
        STATUS      current
        DESCRIPTION "The authoritative identifier for the
                    HP J4887A Switch 4104GL."
        ::= { hpEtherSwitch 27 }

    hpSwitchJ4874A OBJECT-IDENTITY
        STATUS      current
        DESCRIPTION "The authoritative identifier for the
                    HP J4874A Routing Switch 9315."
        ::= { hpEtherSwitch 28 }

    hpSwitchJ4899A OBJECT-IDENTITY
        STATUS      current
        DESCRIPTION "The authoritative identifier for the
                    HP J4899A Switch 2650."
        ::= { hpEtherSwitch 29 }

    hpSwitchJ4902A OBJECT-IDENTITY
        STATUS      current
        DESCRIPTION "The authoritative identifier for the
                    HP J4902A Switch 6108."
        ::= { hpEtherSwitch 30 }

    hpSwitchJ4903A OBJECT-IDENTITY
        STATUS      current
        DESCRIPTION "The authoritative identifier for the
                    HP J4903A Switch 2824."
        ::= { hpEtherSwitch 31 }
    
    hpSwitchJ4904A OBJECT-IDENTITY
        STATUS      current
        DESCRIPTION "The authoritative identifier for the
                    HP J4904A Switch 2848."
        ::= { hpEtherSwitch 32 }

    hpSwitchProliant OBJECT-IDENTITY
        STATUS      current
        DESCRIPTION "The authoritative identifier for the
                    HP Proliant Series Switches."
        ::= { hpEtherSwitch 33 }

    hpSwitchJ4900A OBJECT-IDENTITY
        STATUS      current
        DESCRIPTION "The authoritative identifier for the
                    HP J4900A Switch 2626."
        ::= { hpEtherSwitch 34 }

    hpSwitchJ8165A OBJECT-IDENTITY
        STATUS      current
        DESCRIPTION "The authoritative identifier for the
                    HP J8165A Switch 2650-PWR."
        ::= { hpEtherSwitch 35 }

    hpSwitchJ8164A OBJECT-IDENTITY
        STATUS      current
        DESCRIPTION "The authoritative identifier for the
                    HP J8164A Switch 2626-PWR."
        ::= { hpEtherSwitch 36 }

    hpSwitchJ8130A OBJECT-IDENTITY
        STATUS      obsolete
        DESCRIPTION "The authoritative identifier for the
                    HP J8130A Wireless Access Point AP420WL."
        ::= { hpEtherSwitch 37 }

    hpSwitchJ8133A OBJECT-IDENTITY
        STATUS      current
        DESCRIPTION "The authoritative identifier for the
                    HP J8133A Wireless Access Point AP520WL."
        ::= { hpEtherSwitch 38 }

    hpSwitchJ8153A OBJECT-IDENTITY
        STATUS      current
        DESCRIPTION "The authoritative identifier for the
                    HP J8153A Access Controller 720WL."
        ::= { hpEtherSwitch 39 }

    hpSwitchJ8154A OBJECT-IDENTITY
        STATUS      current
        DESCRIPTION "The authoritative identifier for the
                    HP J8154A Access Controller Server 740WL."
        ::= { hpEtherSwitch 40 }

    hpSwitchJ8155A OBJECT-IDENTITY
        STATUS      current
        DESCRIPTION "The authoritative identifier for the
                    HP J8155A Integrated Access Manager 760WL."
        ::= { hpEtherSwitch 41 }

    hpSwitchJ4905A OBJECT-IDENTITY
        STATUS      current
        DESCRIPTION "The authoritative identifier for the
		    HP J4905A Switch 3400cl-24G."
        ::= { hpEtherSwitch 42 }

    hpSwitchJ4906A OBJECT-IDENTITY
        STATUS      current
        DESCRIPTION "The authoritative identifier for the
		    HP J4906A Switch 3400cl-48G."
        ::= { hpEtherSwitch 43 }

    hpSwitchJ4899B OBJECT-IDENTITY
        STATUS      current
        DESCRIPTION "The authoritative identifier for the
                    HP J4899B Switch 2650-CR."
        ::= { hpEtherSwitch 44 }

    hpSwitchJ4900B OBJECT-IDENTITY
        STATUS      current
        DESCRIPTION "The authoritative identifier for the
                    HP J4900B Switch 2626-CR."
        ::= { hpEtherSwitch 45 }

    hpSwitchJ8718A OBJECT-IDENTITY
        STATUS      current
        DESCRIPTION "The authoritative identifier for the
                    HP J8718A Switch 5404yl."
        ::= { hpEtherSwitch 46 }

    hpSwitchJ8719A OBJECT-IDENTITY
        STATUS      current
        DESCRIPTION "The authoritative identifier for the
                    HP J8719A Switch 5408yl."
        ::= { hpEtherSwitch 47 }

    hpSwitchJ8433A OBJECT-IDENTITY
        STATUS      current
        DESCRIPTION "The authoritative identifier for the
		    HP J8433A Switch 6400cl-6XG."
        ::= { hpEtherSwitch 48 }

    hpSwitchJ8474A OBJECT-IDENTITY
        STATUS      current
        DESCRIPTION "The authoritative identifier for the
		    HP J8474A Switch 6410cl-6XG."
        ::= { hpEtherSwitch 49 }

    hpSwitchJ8697A OBJECT-IDENTITY
        STATUS      current
        DESCRIPTION "The authoritative identifier for the
		    HP J8697A Switch 5406zl."
        ::= { hpEtherSwitch 50 }

    hpSwitchJ8698A OBJECT-IDENTITY
        STATUS      current
        DESCRIPTION "The authoritative identifier for the
		    HP J8698A Switch 5412zl. "
        ::= { hpEtherSwitch 51 }

    hpSwitchJ8770A OBJECT-IDENTITY
        STATUS      current
        DESCRIPTION "The authoritative identifier for the
		    ProCurve J8770A Switch 4204vl."
        ::= { hpEtherSwitch 52 }

    hpSwitchJ8773A OBJECT-IDENTITY
        STATUS      current
        DESCRIPTION "The authoritative identifier for the
		    ProCurve J8773A Switch 4208vl."
        ::= { hpEtherSwitch 53 }

    hpSwitchJ8680A OBJECT-IDENTITY
        STATUS      current
        DESCRIPTION "The authoritative identifier for the
		    HP J8680A Router 9608sl."
        ::= { hpEtherSwitch 54 }

    hpSwitchJ8762A OBJECT-IDENTITY
        STATUS      current
        DESCRIPTION "The authoritative identifier for the
                    HP J8762A Switch 2600-8-PWR."
        ::= { hpEtherSwitch 55 }

    hpSwitchJ8771A OBJECT-IDENTITY
        STATUS      current
        DESCRIPTION "The authoritative identifier for the
                    ProCurve J8771A Switch 4202vl-48G."
        ::= { hpEtherSwitch 56 }

    hpSwitchJ8772A OBJECT-IDENTITY
        STATUS      current
        DESCRIPTION "The authoritative identifier for the
                    ProCurve J8772A Switch 4202vl-72."
        ::= { hpEtherSwitch 57 }

    hpSwitchJ8692A OBJECT-IDENTITY
        STATUS      current
        DESCRIPTION "The authoritative identifier for the
                    HP J8692A Switch 3500yl-24G-PWR."
        ::= { hpEtherSwitch 58 }

    hpSwitchJ8693A OBJECT-IDENTITY
        STATUS      current
        DESCRIPTION "The authoritative identifier for the
                    HP J8693A Switch 3500yl-48G-PWR."
        ::= { hpEtherSwitch 59 }

    
    hpSwitchJ8992A OBJECT-IDENTITY
        STATUS      current
        DESCRIPTION "The authoritative identifier for the
                    HP J8992A Switch 6200yl-24G."
        ::= { hpEtherSwitch 60 }
    hpSwitchJ9019A OBJECT-IDENTITY
        STATUS      current
        DESCRIPTION "The authoritative identifier for the
                    ProCurve J9019A Switch 2510-24A."
        ::= { hpEtherSwitch 61 }

    hpSwitchJ9020A OBJECT-IDENTITY
        STATUS      current
        DESCRIPTION "The authoritative identifier for the
                    ProCurve J9020A Switch 2510-48A."
        ::= { hpEtherSwitch 62 }

    hpSwitchJ9021A OBJECT-IDENTITY
        STATUS      current
        DESCRIPTION "The authoritative identifier for the
                    ProCurve J9021A Switch 2810-24G."
        ::= { hpEtherSwitch 63 }

    hpSwitchJ9022A OBJECT-IDENTITY
        STATUS      current
        DESCRIPTION "The authoritative identifier for the
                    ProCurve J9022A Switch 2810-48G."
        ::= { hpEtherSwitch 64 }

    hpSwitchJ9028A OBJECT-IDENTITY
        STATUS      current
        DESCRIPTION "The authoritative identifier for the
                    ProCurve J9028A Switch 1800-24G."
        ::= { hpEtherSwitch 65 }

    hpSwitchJ9029A OBJECT-IDENTITY
        STATUS      current
        DESCRIPTION "The authoritative identifier for the
                    ProCurve J9029A Switch 1800-8G."
        ::= { hpEtherSwitch 66 }

    hpSwitchJ9038A OBJECT-IDENTITY
        STATUS      current
        DESCRIPTION "The authoritative identifier for the
                    ProCurve J9038A device."
        ::= { hpEtherSwitch 67 }

    hpSwitchJ9050A OBJECT-IDENTITY
        STATUS      current
        DESCRIPTION "The authoritative identifier for the
                    HP J9050A Switch 2900-48G."
        ::= { hpEtherSwitch 68 }

    hpSwitchJ9049A OBJECT-IDENTITY
        STATUS      current
        DESCRIPTION "The authoritative identifier for the
                    HP J9049A Switch 2900-24G."
        ::= { hpEtherSwitch 69 }

    hpSwitchJ9032A OBJECT-IDENTITY
        STATUS      current
        DESCRIPTION "The authoritative identifier for the
                    ProCurve J9032A Switch 4202vl-68G."
        ::= { hpEtherSwitch 70 }

    hpSwitchJ9031A OBJECT-IDENTITY
        STATUS      current
        DESCRIPTION "The authoritative identifier for the
                    ProCurve J9031A Switch 4202vl-68. (DO NOT PUBLISH)"
        ::= { hpEtherSwitch 71 }

    hpSwitchJ8715A OBJECT-IDENTITY
        STATUS      current
        DESCRIPTION "The authoritative identifier for the
		    HP J8715A Switch 8200zl. "
        ::= { hpEtherSwitch 72 }

    -- different cards for Switch 2000

    hpSwitchPortModuleET4 OBJECT-IDENTITY
        STATUS      current
        DESCRIPTION "The authoritative identifier for the
                    HP J3102A AdvanceStack Switch Ethernet Port
                    Module."
        ::= { hpAdvSwitch2000 1 }

    hpSwitchPortModuleVG2 OBJECT-IDENTITY
        STATUS      current
        DESCRIPTION "The authoritative identifier for the
                    HP J3103A AdvanceStack Switch 100VG Port
                    Module."
        ::= { hpAdvSwitch2000 2 }

    hpSwitchPortModule10FL OBJECT-IDENTITY
        STATUS      current
        DESCRIPTION "The authoritative identifier for the
                    HP AdvanceStack Switch 10BaseFL Port Module."
        ::= { hpAdvSwitch2000 3 }

    hpSwitchPortModuleFDDI OBJECT-IDENTITY
        STATUS      current
        DESCRIPTION "The authoritative identifier for the
                    HP AdvanceStack Switch FDDI Port Module."
        ::= { hpAdvSwitch2000 4 }

    hpSwitchPortModuleTX2 OBJECT-IDENTITY
        STATUS      current
        DESCRIPTION "The authoritative identifier for the
                    HP AdvanceStack Switch 100BaseT Port Module."
        ::= { hpAdvSwitch2000 5 }

    hpSwitchPortModuleATM OBJECT-IDENTITY
        STATUS      current
        DESCRIPTION "The authoritative identifier for the
                    HP AdvanceStack Switch ATM Port Module."
        ::= { hpAdvSwitch2000 6 }

    -- different cards for Switch 8000/4000/1600/2400/2424 family

    hpSwitchPortModule100TX8 OBJECT-IDENTITY
        STATUS      current
        DESCRIPTION "The authoritative identifier for the
                    HP J4111A 8-port 10/100Base-TX module."
        ::= { hpSwitch8000 1 }

    hpSwitchPortModule100FX4 OBJECT-IDENTITY
        STATUS      current
        DESCRIPTION "The authoritative identifier for the
                    HP J4112A 4-port 100Base-FX module."
        ::= { hpSwitch8000 2 }

    hpSwitchPortModule10FL4 OBJECT-IDENTITY
        STATUS      current
        DESCRIPTION "The authoritative identifier for the
                    HP J4118A 4-port 10Base-FL module."
        ::= { hpSwitch8000 3 }

    hpSwitchPortModuleGigSX OBJECT-IDENTITY
        STATUS      current
        DESCRIPTION "The authoritative identifier for the
                    HP J4113A 1-port Gigabit SX module."
        ::= { hpSwitch8000 4 }

    hpSwitchPortModuleGigLX OBJECT-IDENTITY
        STATUS      current
        DESCRIPTION "The authoritative identifier for the
                    HP J4114A 1-port Gigabit LX module."
        ::= { hpSwitch8000 5 }

    hpSwitchPortModuleTwoGig OBJECT-IDENTITY
        STATUS      current
        DESCRIPTION "The authoritative identifier for the
                    HP J4130A 2-port Gigabit module."
        ::= { hpSwitch8000 6 }

    hpSwitchPortModuleGigStk OBJECT-IDENTITY
        STATUS      current
        DESCRIPTION "The authoritative identifier for the
                    HP J4130A 1-port Gigabit Stacking module."
        ::= { hpSwitch8000 7 }

    hpSwitchPortModuleGigT OBJECT-IDENTITY
        STATUS      current
        DESCRIPTION "The authoritative identifier for the
                    HP J4115A 1-port Gigabit T module."
        ::= { hpSwitch8000 8 }


    -- different cards for Switch 5308 family

    hpSwitchPortModuleJ4820A OBJECT-IDENTITY
        STATUS      current
        DESCRIPTION "The authoritative identifier for the
                    HP J4820A 24 Port 10/100Base-TX Module."
        ::= { hpSwitchJ4819A 1 }

    hpSwitchPortModuleJ4821A OBJECT-IDENTITY
        STATUS      current
        DESCRIPTION "The authoritative identifier for the
                    HP J4821A 4 Port 100/1000Base-TX Module."
        ::= { hpSwitchJ4819A 2 }

    hpSwitchPortModuleJ4878A OBJECT-IDENTITY
        STATUS      current
        DESCRIPTION "The authoritative identifier for the
                    HP J4878A 4x MiniGBIC Module."
        ::= { hpSwitchJ4819A 3 }
    
    hpSwitchModuleJ4852A OBJECT-IDENTITY
        STATUS      current
        DESCRIPTION "The authoritative identifier for the
                    HP J4852A 12-port 100-FX MTRJ" 
        ::= { hpSwitchJ4819A 4 }

    hpSwitchModuleJ8161A OBJECT-IDENTITY
        STATUS      current
        DESCRIPTION "The authoritative identifier for the
                    HP J8161A 24-port 10/100Base-TX PoE Module." 
        ::= { hpSwitchJ4819A 5 }

    hpSwitchModuleJ4907A OBJECT-IDENTITY
        STATUS      current
        DESCRIPTION "The authoritative identifier for the
                    HP J4907A Gig-T/GBIC xl Module." 
        ::= { hpSwitchJ4819A 6 }

    hpSwitchModuleJ8162A OBJECT-IDENTITY
        STATUS      current
        DESCRIPTION "The authoritative identifier for the
                    HP J8162A XL Access Controller Module." 
        ::= { hpSwitchJ4819A 7 }

    hpSwitchPortModuleJ4820B OBJECT-IDENTITY
        STATUS      current
        DESCRIPTION "The authoritative identifier for the
                    HP J4820B 24 Port 10/100Base-TX Module."
        ::= { hpSwitchJ4819A 8 }

    hpSwitchPortModuleJ4821B OBJECT-IDENTITY
        STATUS      current
        DESCRIPTION "The authoritative identifier for the
                    HP J4821B 4 Port 100/1000Base-TX Module."
        ::= { hpSwitchJ4819A 9 }

    hpSwitchPortModuleJ4878B OBJECT-IDENTITY
        STATUS      current
        DESCRIPTION "The authoritative identifier for the
                    HP J4878B 4x MiniGBIC Module."
        ::= { hpSwitchJ4819A 10 }

    hpSwitchModuleJ9001A OBJECT-IDENTITY
        STATUS      current
        DESCRIPTION "The authoritative identifier for the
                    HP J9001A Module." 
        ::= { hpSwitchJ4819A 11 }

    hpSwitchModuleJ9003A OBJECT-IDENTITY
        STATUS      current
        DESCRIPTION "The authoritative identifier for the
                    HP J9003A Module." 
        ::= { hpSwitchJ4819A 12 }

    hpSwitchModuleJ8988A OBJECT-IDENTITY
        STATUS      current
        DESCRIPTION "The authoritative identifier for the
		    ProCurve J8988A 10-GbE xl module. (DO NOT PUBLISH)"
        ::= { hpSwitchJ4819A 13 }  

    -- different pseudo cards for Switch 2524/2512 family

    hpSwitchModuleJ4812A OBJECT-IDENTITY
        STATUS      current
        DESCRIPTION "The authoritative identifier for the
                    HP J4812A 12-port 10/100Base-TX + 2 Gig
                    module"
        ::= { hpSwitchJ4812A 1 }

    hpSwitchModuleJ4813A OBJECT-IDENTITY
        STATUS      current
        DESCRIPTION "The authoritative identifier for the
                    HP J4813A 24-port 10/100Base-TX + 2 Gig 
                    module"
        ::= { hpSwitchJ4813A 1 }

    -- different pseudo cards for Switch 4865 family

    hpSwitchModuleJ4862A OBJECT-IDENTITY
        STATUS      current
        DESCRIPTION "The authoritative identifier for the
                    HP J4862A 24-port 10/100Base-TX" 
        ::= { hpSwitchJ4865A 1 }

    hpSwitchModuleJ4863A OBJECT-IDENTITY
        STATUS      current
        DESCRIPTION "The authoritative identifier for the
                    HP J4863A 6-port 100/1000Base-TX" 
        ::= { hpSwitchJ4865A 2 }

    hpSwitchModuleJ4864A OBJECT-IDENTITY
        STATUS      current
        DESCRIPTION "The authoritative identifier for the
                    HP J4864A 3-port tranceiver module"
        ::= { hpSwitchJ4865A 3 }

    hpSwitchModuleJ4862B OBJECT-IDENTITY
        STATUS      current
        DESCRIPTION "The authoritative identifier for the
                    HP J4862B 24-port 10/100Base-TX" 
        ::= { hpSwitchJ4865A 4 }

    hpSwitchModuleJ4893A OBJECT-IDENTITY
        STATUS      current
        DESCRIPTION "The authoritative identifier for the
                    HP J4893A 6-port Mini-GBIC module" 
        ::= { hpSwitchJ4865A 5 }

    hpSwitchModuleJ4892A OBJECT-IDENTITY
        STATUS      current
        DESCRIPTION "The authoritative identifier for the
                    HP J4892A 12-port 100-FX MTRJ" 
        ::= { hpSwitchJ4865A 6 }
    
    hpSwitchModuleJ4908A OBJECT-IDENTITY
        STATUS      current
        DESCRIPTION "The authoritative identifier for the
                    HP J489XA 20-port 10/100/1000Base-TX + 2 Mini-GBIC" 
        ::= { hpSwitchJ4865A 7 }
    
    hpSwitchModuleJ4903A OBJECT-IDENTITY
        STATUS      current
        DESCRIPTION "The authoritative identifier for the
                    HP J4903A 24-port 10/100/1000Base-TX" 
        ::= { hpSwitchJ4903A 1 }

    hpSwitchModuleJ8434A OBJECT-IDENTITY
        STATUS      current
        DESCRIPTION "The authoritative identifier for the
                    HP J8434A 2-port 10G CX4"
        ::= { hpSwitchJ4903A 2}

    hpSwitchModuleJ8435A OBJECT-IDENTITY
        STATUS      current
        DESCRIPTION "The authoritative identifier for the
                    HP J8435A 2-port 10G MF"
        ::= { hpSwitchJ4903A 3}

    hpSwitchModuleJ4904A OBJECT-IDENTITY
        STATUS      current
        DESCRIPTION "The authoritative identifier for the
                    HP J4904A 48-port 10/100/1000Base-TX" 
        ::= { hpSwitchJ4904A 1 }
    
    -- psuedo cards for the 3400/6400 family        
    
    hpSwitchModuleJ4905A OBJECT-IDENTITY
        STATUS      current
        DESCRIPTION "The authoritative identifier for the
		    HP J4905A Switch 3400cl-24G."
        ::= { hpSwitchJ4905A 1 }
    
    hpSwitchModuleJ4906A OBJECT-IDENTITY
        STATUS      current
        DESCRIPTION "The authoritative identifier for the
		    HP J4906A Switch 3400cl-48G."
        ::= { hpSwitchJ4906A 1 }

    hpSwitchModuleJ8433A OBJECT-IDENTITY
        STATUS      current
        DESCRIPTION "The authoritative identifier for the
		    HP J8433A Switch 6400cl-6XG."
        ::= { hpSwitchJ8433A 1 }

    hpSwitchModuleJ8474A OBJECT-IDENTITY
        STATUS      current
        DESCRIPTION "The authoritative identifier for the
		    HP J8474A Switch 6410cl-6XG ."
        ::= { hpSwitchJ8474A 1 }

    hpSwitchModuleJ8701A OBJECT-IDENTITY
        STATUS      current
        DESCRIPTION "The authoritative identifier for the
		    HP J8701A 24 port Gig-T."
        ::= { hpSwitchJ8697A 1 }
    
    hpSwitchModuleJ8702A OBJECT-IDENTITY
        STATUS      current
        DESCRIPTION "The authoritative identifier for the
		    HP J8702A 24 port Gig-T zl Module."
        ::= { hpSwitchJ8697A 2 }

    hpSwitchModuleJ8705A OBJECT-IDENTITY
        STATUS      current
        DESCRIPTION "The authoritative identifier for the
		    HP J8705A Gig-T/SFP zl Module."
        ::= { hpSwitchJ8697A 3 }

    hpSwitchModuleJ8706A OBJECT-IDENTITY
        STATUS      current
        DESCRIPTION "The authoritative identifier for the
		    HP J8706A 24 port SFP zl Module. "
        ::= { hpSwitchJ8697A 4 }

   hpSwitchModuleJ8707A OBJECT-IDENTITY
        STATUS      current
        DESCRIPTION "The authoritative identifier for the
                    HP J8707A 4 port 10-GbE zl Module."
        ::= { hpSwitchJ8697A 5 }

   hpSwitchModuleJ8708A OBJECT-IDENTITY
        STATUS      current
        DESCRIPTION "The authoritative identifier for the
                    HP J8708A 4 port 10G CX4 zl Module. "
        ::= { hpSwitchJ8697A 6 }


   hpSwitchModuleJ87xxA OBJECT-IDENTITY
        STATUS      current
        DESCRIPTION "The authoritative identifier for the
                    HP J87xxA yl Fixed Gig-T/SFP."
        ::= { hpSwitchJ8697A 7 }

   hpSwitchModuleJ87yyA OBJECT-IDENTITY
        STATUS      current
        DESCRIPTION "The authoritative identifier for the
                    HP J87yyA yl Fixed 24p Gig-T."
        ::= { hpSwitchJ8697A 8 }

   hpSwitchModuleJ8694A OBJECT-IDENTITY
        STATUS      current
        DESCRIPTION "The authoritative identifier for the
                    HP J8694A yl X2/CX4 10-GbE Module."
        ::= { hpSwitchJ8697A 9 }

   hpSwitchModuleJ8726A OBJECT-IDENTITY
        STATUS      current
        DESCRIPTION "The authoritative identifier for the
                    HP J8726A 5400 zl Management Module."
        ::= { hpSwitchJ8697A 10 }
 hpSwitchModuleJ90xxA OBJECT-IDENTITY
        STATUS      current
        DESCRIPTION "The authoritative identifier for the
                    HP J9050A yl Fixed Gig-T/SFP."
        ::= { hpSwitchJ9050A 11 }

   hpSwitchModuleJ90yyA OBJECT-IDENTITY
        STATUS      current
        DESCRIPTION "The authoritative identifier for the
                    HP J9050A yl Fixed 24p Gig-T."
        ::= { hpSwitchJ9050A 12 }

   hpSwitchModuleJ90zzA OBJECT-IDENTITY
        STATUS      current
        DESCRIPTION "The authoritative identifier for the
                    HP J9050A yl X2/CX4 10-GbE Module."
        ::= { hpSwitchJ9050A 13 }

   hpSwitchModuleJ9051A OBJECT-IDENTITY
        STATUS      current
        DESCRIPTION "The authoritative identifier for the
                    HP J9051A Wireless services Primary zl Module."
        ::= { hpSwitchJ8697A 14 }

   hpSwitchModuleJ9052A OBJECT-IDENTITY
        STATUS      current
        DESCRIPTION "The authoritative identifier for the
                    HP J9052A Wireless services Redundant zl Module."
        ::= { hpSwitchJ8697A 15 }


    -- different cards for the 4200 family

    hpSwitchModuleJ8765A OBJECT-IDENTITY
        STATUS      current
        DESCRIPTION "The authoritative identifier for the
		    ProCurve J8765A 10/100 module."
        ::= { hpSwitchJ8770A 1 }  

    hpSwitchModuleJ8764A OBJECT-IDENTITY
        STATUS      current
        DESCRIPTION "The authoritative identifier for the
		    ProCurve J8764A 10/100/1000 module."
        ::= { hpSwitchJ8770A 2 }        

    hpSwitchModuleJ8776A OBJECT-IDENTITY
        STATUS      current
        DESCRIPTION "The authoritative identifier for the
		    ProCurve J8776A miniGBIC module."
        ::= { hpSwitchJ8770A 3 }  

    hpSwitchModuleJ8763A OBJECT-IDENTITY
        STATUS      current
        DESCRIPTION "The authoritative identifier for the
		    ProCurve J8763A 100FX module."
        ::= { hpSwitchJ8770A 4 } 
	 
    hpSwitchModuleJ8768A OBJECT-IDENTITY
        STATUS      current
        DESCRIPTION "The authoritative identifier for the
		    ProCurve J8768A Gig-T vl module."
        ::= { hpSwitchJ8770A 5 }  

    hpSwitchModuleJ9033A OBJECT-IDENTITY
        STATUS      current
        DESCRIPTION "The authoritative identifier for the
		    ProCurve J9033A Gig-T/SFP vl module."
        ::= { hpSwitchJ8770A 6 }  

    hpSwitchModuleJ9037A OBJECT-IDENTITY
        STATUS      current
        DESCRIPTION "The authoritative identifier for the
		    ProCurve J9037A 10/100Base-TX + SFP vl module. (DO NOT PUBLISH)"
        ::= { hpSwitchJ8770A 7 }  

    hpSwitchModuleJ8765B OBJECT-IDENTITY
        STATUS      current
        DESCRIPTION "The authoritative identifier for the
		    ProCurve J8765B 10/100-TX vl module. (DO NOT PUBLISH)"
        ::= { hpSwitchJ8770A 8 }  

    hpSwitchModuleJ9036A OBJECT-IDENTITY
        STATUS      current
        DESCRIPTION "The authoritative identifier for the
		    ProCurve J9036A SFP vl module. (DO NOT PUBLISH)"
        ::= { hpSwitchJ8770A 9 }  

    hpSwitchModuleJ8766A OBJECT-IDENTITY
        STATUS      current
        DESCRIPTION "The authoritative identifier for the
		    ProCurve J8766A 10-GbE vl module. (DO NOT PUBLISH)"
        ::= { hpSwitchJ8770A 10 }  

    hpSwitchModuleJ9021A OBJECT-IDENTITY
        STATUS      current
        DESCRIPTION "The authoritative identifier for the
		    HP J9021A Switch 2810-24G."
        ::= { hpSwitchJ9021A 1 }  

    hpSwitchModuleJ9022A OBJECT-IDENTITY
        STATUS      current
        DESCRIPTION "The authoritative identifier for the
		    HP J9022A Switch 2810-48G."
        ::= { hpSwitchJ9022A 1 }  

    hpSwitchModuleJ9019A OBJECT-IDENTITY
        STATUS      current
        DESCRIPTION "The authoritative identifier for the
		    HP J9019A Switch 2510-24A."
        ::= { hpSwitchJ9019A 1 }  

    hpSwitchModuleJ9020A OBJECT-IDENTITY
        STATUS      current
        DESCRIPTION "The authoritative identifier for the
		    HP J9020A Switch 2510-48A."
        ::= { hpSwitchJ9020A 1 }  

    -- WAN Products

    -- Branches under the hpicfWan node
    hpWANRouters          OBJECT IDENTIFIER ::= { hpicfWAN 1 }
    hpWANModules          OBJECT IDENTIFIER ::= { hpicfWAN 2 }

    -- WAN Routers 

    hpSRJ8751A OBJECT-IDENTITY
        STATUS      current
        DESCRIPTION "The authoritative identifier for the
                    HP J8751A Secure Router 7001dl." 
        ::= { hpWANRouters 1 }

    hpSRJ8752A OBJECT-IDENTITY
        STATUS      current
        DESCRIPTION "The authoritative identifier for the
                    HP J8752A Secure Router 7102dl." 
        ::= { hpWANRouters 2 }

    hpSRJ8753A OBJECT-IDENTITY
        STATUS      current
        DESCRIPTION "The authoritative identifier for the
                    HP J8753A Secure Router 7203dl." 
        ::= { hpWANRouters 3 }

    hpSRJ8754A OBJECT-IDENTITY
        STATUS      current
        DESCRIPTION "The authoritative identifier for the
                    HP J8754A Secure Router 7306dl." 
        ::= { hpWANRouters 4 }    

   -- WAN Modules

   hpSRmoduleJ8451A OBJECT-IDENTITY
        STATUS      current
        DESCRIPTION "The authoritative identifier for the
                    HP ProCurve SR dl 1 x T1 module." 
        ::= { hpWANModules 1 }

   hpSRmoduleJ8452A OBJECT-IDENTITY
        STATUS      current
        DESCRIPTION "The authoritative identifier for the
                    HP ProCurve SR dl 1 x T1 + DSX-1 module." 
        ::= { hpWANModules 2 }

   hpSRmoduleJ8453A OBJECT-IDENTITY
        STATUS      current
        DESCRIPTION "The authoritative identifier for the
                    HP ProCurve SR dl 2 x T1 module." 
        ::= { hpWANModules 3 }

   hpSRmoduleJ8454A OBJECT-IDENTITY
        STATUS      current
        DESCRIPTION "The authoritative identifier for the
                    HP ProCurve SR dl 1 x E1 module." 
        ::= { hpWANModules 4 }

   hpSRmoduleJ8455A OBJECT-IDENTITY
        STATUS      current
        DESCRIPTION "The authoritative identifier for the
                    HP ProCurve SR dl 1 x E1 + G.703 module." 
        ::= { hpWANModules 5 }

   hpSRmoduleJ8456A OBJECT-IDENTITY
        STATUS      current
        DESCRIPTION "The authoritative identifier for the
                    HP ProCurve SR dl 2 x E1 module." 
        ::= { hpWANModules 6 }

   hpSRmoduleJ8457A OBJECT-IDENTITY
        STATUS      current
        DESCRIPTION "The authoritative identifier for the
                    HP ProCurve SR dl 2 x ISDN BRI S/T module." 
        ::= { hpWANModules 7 }

   hpSRmoduleJ8458A OBJECT-IDENTITY
        STATUS      current
        DESCRIPTION "The authoritative identifier for the
                    HP ProCurve SR dl 1 x Serial module." 
        ::= { hpWANModules 8 }

   hpSRmoduleJ8459A OBJECT-IDENTITY
        STATUS      current
        DESCRIPTION "The authoritative identifier for the
                    HP ProCurve SR dl 1 x ADSL2+ Annex A module." 
        ::= { hpWANModules 9 }

   hpSRmoduleJ8759A OBJECT-IDENTITY
        STATUS      current
        DESCRIPTION "The authoritative identifier for the
                    HP ProCurve SR dl 1 x ADSL2+ Annex B module."
        ::= { hpWANModules 10 }

   hpSRmoduleJ8460A OBJECT-IDENTITY
        STATUS      current
        DESCRIPTION "The authoritative identifier for the
                    HP ProCurve SR dl ISDN BRI U backup." 
        ::= { hpWANModules 11 }

   hpSRmoduleJ8461A OBJECT-IDENTITY
        STATUS      current
        DESCRIPTION "The authoritative identifier for the
                    HP ProCurve SR dl ISDN BRI S/T backup." 
        ::= { hpWANModules 12 }

   hpSRmoduleJ8462A OBJECT-IDENTITY
        STATUS      current
        DESCRIPTION "The authoritative identifier for the
                    HP ProCurve SR dl Analog Modem backup." 
        ::= { hpWANModules 13 }

   hpSRmoduleJ8463A OBJECT-IDENTITY
        STATUS      current
        DESCRIPTION "The authoritative identifier for the
                    HP ProCurve SR dl 8 x T1/E1 wide module." 
        ::= { hpWANModules 14 }

   hpSRmoduleJ8464A OBJECT-IDENTITY
        STATUS      current
        DESCRIPTION "The authoritative identifier for the
                    HP ProCurve SR dl DS-3 wide module." 
        ::= { hpWANModules 15 }

   hpSRmoduleJ8465A OBJECT-IDENTITY
        STATUS      current
        DESCRIPTION "The authoritative identifier for the
                    HP ProCurve SR dl HSSI wide  module." 
        ::= { hpWANModules 16 }

   hpSRmoduleJ8471A OBJECT-IDENTITY
        STATUS      current
        DESCRIPTION "The authoritative identifier for the
                    HP ProCurve SR 7100/7200 IPSec module." 
        ::= { hpWANModules 17 }

   hpSRmoduleJ8472A OBJECT-IDENTITY
        STATUS      current
        DESCRIPTION "The authoritative identifier for the
                    HP ProCurve SR 7300 series IPSec module." 
        ::= { hpWANModules 18 }

-- Accessories for 7300 series WAN Secure Router

    hpSRPowerSupply8756A OBJECT-IDENTITY
        STATUS            current
        DESCRIPTION "The authoritative identifier for the
                    HP J8754A Secure Router 7306dl powersupply." 
        ::= { hpSRJ8754A 1 }    

END
