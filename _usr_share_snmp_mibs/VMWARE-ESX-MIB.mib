VMWARE-ESX-MIB DEFINITIONS ::= BEGIN

IMPORTS
    OBJECT-TYPE 
      FROM RFC1155-SMI

   DisplayString 
      FROM RFC1213-MIB

   vmwOID, vmwProductSpecific 
      FROM VMWARE-ROOT-MIB;

oidESX OBJECT IDENTIFIER ::= { vmwOID 1 }

-- This file contains the MIB for VMware ESX Server specific variables. 
vmwESX OBJECT IDENTIFIER ::= { vmwProductSpecific 1 }

-- ESX VMKernel variables 
esxVMKernel OBJECT IDENTIFIER ::= { vmwESX 1 }

vmkLoaded OBJECT-TYPE 
   SYNTAX      DisplayString
   ACCESS      read-only
   STATUS      mandatory
   DESCRIPTION
      "Has the vmkernel been loaded? (yes/no)"
   ::= { esxVMKernel 1 }

END
