--
--
--  BlueArc Titan Server Enterprise MIB Module
--
--

BLUEARC-TITAN-MIB DEFINITIONS ::= BEGIN

IMPORTS
    MODULE-IDENTITY, OBJECT-TYPE, Integer32,
    Unsigned32, Counter32, Counter64,
    IpAddress, mib-2, enterprises             FROM SNMPv2-SMI
    DisplayString                             FROM SNMPv2-TC
    MODULE-COMPLIANCE, OBJECT-GROUP           FROM SNMPv2-CONF
    blueArc, blueArcPrivate                   FROM BLUEARC-SERVER-MIB;

blueArcTitan MODULE-IDENTITY
    LAST-UPDATED "201210051200Z"
    ORGANIZATION "BlueArc UK Ltd."
    CONTACT-INFO
                 "Contact:  Central Support

                   Postal:  BlueArc UK Ltd.,
                            Queensgate House,
                            Cookham Road,
                            Bracknell, RG12 1RB,
                            United Kingdom.

                      Tel:  +44(0)1344 408 200
                      Fax:  +44(0)1344 408 202

                      WEB:  http://www.bluearc.com
                    email:  centralsupport@bluearc.com"
    DESCRIPTION
                 "The MIB module for monitoring a BlueArc Titan Server."
    REVISION
                 "201210051200Z"
    DESCRIPTION
                 "Obsolete all package objects, which are
                  no longer to be reported by the agent."
    REVISION
                 "200711051200Z"
    DESCRIPTION
                 "Obsolete FTP user and mount point objects, which are
                  no longer to be reported by the agent."
    REVISION
                 "200604241200Z"
    DESCRIPTION
                 "Obsolete NVRAM objects, and re-implement in BLUEARC_SERVER_MIB."
    REVISION
                 "200402201200Z"
    DESCRIPTION
                 "Define objects for reporting FTP configuration, mount points,
                 users and statistics.
                 
                 Obsolete NVRAM objects, and re-implement in a table indexed
                 by Cluster Node."
    REVISION
                 "200311281200Z"
    DESCRIPTION
                 "Obsolete all quota template and quota objects, and
                 re-implement them using Counter64 data types for
                 usage and usage-limit objects."
    REVISION
                 "200306161200Z"
    DESCRIPTION
                 "Initial Revision 16 Jun 2003 12:00 GMT."

::= { blueArcPrivate 2 }

--------------------------------------------------------------------------------
--
-- MIB Tree Structure
--
--------------------------------------------------------------------------------

    blueArcTitanObjs                    OBJECT IDENTIFIER ::= { blueArcTitan 1 }
        systemTitan                     OBJECT IDENTIFIER ::= { blueArcTitanObjs 1 }
        storageTitan                    OBJECT IDENTIFIER ::= { blueArcTitanObjs 2 }
            virtualVolumesTitan         OBJECT IDENTIFIER ::= { storageTitan 1 }
            nvram                       OBJECT IDENTIFIER ::= { storageTitan 2 }
        networkTitan                    OBJECT IDENTIFIER ::= { blueArcTitanObjs 3 }
            ethernetTitan               OBJECT IDENTIFIER ::= { networkTitan 1}
                linkAggregation         OBJECT IDENTIFIER ::= { ethernetTitan 1 }
        mgmntTitan                      OBJECT IDENTIFIER ::= { blueArcTitanObjs 4 }
            packageMgmnt                OBJECT IDENTIFIER ::= { mgmntTitan 1 }
        fileProtocolTitan               OBJECT IDENTIFIER ::= { blueArcTitanObjs 5 }
            ftpTitan                    OBJECT IDENTIFIER ::= { fileProtocolTitan 1}
                ftpConfig               OBJECT IDENTIFIER ::= { ftpTitan 1 }
                ftpMountpoints          OBJECT IDENTIFIER ::= { ftpTitan 2 }
                ftpUser                 OBJECT IDENTIFIER ::= { ftpTitan 3 }
                ftpStatistics           OBJECT IDENTIFIER ::= { ftpTitan 4 }

--------------------------------------------------------------------------------
--
-- StorageTitan / Virtual Volumes
--
--------------------------------------------------------------------------------

    virtualVolumeTitanNumber OBJECT-TYPE
        SYNTAX Integer32 (1..2147483647)
        MAX-ACCESS read-only
        STATUS current
        DESCRIPTION
            "The number of virtual volumes which are currently accessible.
             NOTE: a virtual volume is only accessible if its associated
                   parent volume is mounted."
        ::= { virtualVolumesTitan 1 }

    virtualVolumeTitanTable OBJECT-TYPE
        SYNTAX SEQUENCE OF VirtualVolumeTitanEntry
        MAX-ACCESS not-accessible
        STATUS current
        DESCRIPTION
            "A table containing information about each virtual volume.

             The number of entries in this table is given by the value of
             virtualVolumeTitanNumber."
        ::= { virtualVolumesTitan 2 }

    virtualVolumeTitanEntry OBJECT-TYPE
        SYNTAX VirtualVolumeTitanEntry
        MAX-ACCESS not-accessible
        STATUS current
        DESCRIPTION
            "Information about a virtual volume."
        INDEX { virtualVolumeTitanSpanId, virtualVolumeTitanName }
        ::= { virtualVolumeTitanTable 1 }

    VirtualVolumeTitanEntry ::=
        SEQUENCE {
            virtualVolumeTitanSpanId
                Unsigned32,
            virtualVolumeTitanName
                DisplayString,
            virtualVolumeTitanPath
                DisplayString,
            virtualVolumeTitanEmailNumber
                Integer32,
            virtualVolumeTitanQuotaNumber
                Integer32
        }

    virtualVolumeTitanSpanId OBJECT-TYPE
        SYNTAX Unsigned32 (1..4294967295)
        MAX-ACCESS read-only
        STATUS current
        DESCRIPTION
            "The parent device of the virtual volume.
             The device identified by a particular value of this index is
             the span underlying the volume hosting the Virtual Volume."
        ::= { virtualVolumeTitanEntry 1 }

    virtualVolumeTitanName OBJECT-TYPE
        SYNTAX DisplayString
        MAX-ACCESS read-only
        STATUS current
        DESCRIPTION
            "The name assigned to the virtual volume by a user for
             identification purposes."
        ::= { virtualVolumeTitanEntry 2 }

    virtualVolumeTitanPath OBJECT-TYPE
        SYNTAX DisplayString
        MAX-ACCESS read-only
        STATUS current
        DESCRIPTION
            "The path to the root of this Virtual Volume."
        ::= { virtualVolumeTitanEntry 3 }

    virtualVolumeTitanEmailNumber OBJECT-TYPE
        SYNTAX Integer32 (1..2147483647)
        MAX-ACCESS read-only
        STATUS current
        DESCRIPTION
            "The number of email addresses associated with this
            Virtual Volume."
        ::= { virtualVolumeTitanEntry 4 }

    virtualVolumeTitanQuotaNumber OBJECT-TYPE
        SYNTAX Integer32 (1..2147483647)
        MAX-ACCESS read-only
        STATUS current
        DESCRIPTION
            "The number of quotas associated with this
            Virtual Volume."
        ::= { virtualVolumeTitanEntry 5 }

    virtualVolumeTitanEmailTable OBJECT-TYPE
        SYNTAX SEQUENCE OF VirtualVolumeTitanEmailEntry
        MAX-ACCESS not-accessible
        STATUS current
        DESCRIPTION
            "A table containing the email address associated with
            this Virtual Volume.

             The number of entries in this table is given by the value of
             virtualVolumeTitanEmailNumber, in virtualVolumeTitanTable."
        ::= { virtualVolumesTitan 3 }

    virtualVolumeTitanEmailEntry OBJECT-TYPE
        SYNTAX VirtualVolumeTitanEmailEntry
        MAX-ACCESS not-accessible
        STATUS current
        DESCRIPTION
            "An email address associated with a Virtual Volume,
            which is uniquely identified by virtualVolumeTitanSpanId
            and virtualVolumeTitanName in virtualVolumeTitanTable."
        INDEX { virtualVolumeTitanSpanId, virtualVolumeTitanName, virtualVolumeTitanEmailAddress }
        ::= { virtualVolumeTitanEmailTable 1 }

    VirtualVolumeTitanEmailEntry ::=
        SEQUENCE {
            virtualVolumeTitanEmailAddress
                DisplayString
        }

    virtualVolumeTitanEmailAddress OBJECT-TYPE
        SYNTAX DisplayString
        MAX-ACCESS read-only
        STATUS current
        DESCRIPTION
            "An email address associated with a Virtual Volume."
        ::= { virtualVolumeTitanEmailEntry 1 }

    virtualVolumeTitanQuotaTemplateTable OBJECT-TYPE
        SYNTAX SEQUENCE OF VirtualVolumeTitanQuotaTemplateEntry
        MAX-ACCESS not-accessible
        STATUS obsolete
        DESCRIPTION
            "A table containing quota templates associated with
            Virtual Volumes. The template is indexed by the values
            virtualVolumeTitanSpanId and virtualVolumeTitanTarget in
            virtualVolumeTitanTable, and the
            virtualVolumeQuotaTemplateTargetType.

            The two types of quota template are: user quota template,
            and group quota template. The templates define the
            default quota settings which will be used to create a
            Default Quota when a user or group begins to use the Virtual
            Volume. Once the default quota has been created, a user
            or group's quota may be modified, whence it will become an
            Explicit Quota.

            This object is now obsolete."
        ::= { virtualVolumesTitan 4 }

    virtualVolumeTitanQuotaTemplateEntry OBJECT-TYPE
        SYNTAX VirtualVolumeTitanQuotaTemplateEntry
        MAX-ACCESS not-accessible
        STATUS obsolete
        DESCRIPTION
            "A quota template associated with a Virtual Volume.
            The template is indexed by the values virtualVolumeTitanSpanId
            and virtualVolumeTitanTarget in virtualVolumeTitanTable, and 
            the virtualVolumeQuotaTemplateTargetType.

            This object is now obsolete."
        INDEX { virtualVolumeTitanSpanId, virtualVolumeTitanName, virtualVolumeQuotaTemplateTargetType }
        ::= { virtualVolumeTitanQuotaTemplateTable 1 }

    VirtualVolumeTitanQuotaTemplateEntry ::=
        SEQUENCE {
            virtualVolumeQuotaTemplateTargetType
                INTEGER,
            virtualVolumeQuotaTemplateIgnoreWellKnownGroups
                INTEGER,
            virtualVolumeTitanQuotaTemplateUsageLimit
                Unsigned32,
            virtualVolumeTitanQuotaTemplateUsageHardLimit
                INTEGER,
            virtualVolumeTitanQuotaTemplateUsageReset
                Unsigned32,
            virtualVolumeTitanQuotaTemplateUsageWarning
                Unsigned32,
            virtualVolumeTitanQuotaTemplateUsageCritical
                Unsigned32,
            virtualVolumeTitanQuotaTemplateFileCountLimit
                Unsigned32,
            virtualVolumeTitanQuotaTemplateFileCountHardLimit
                INTEGER,
            virtualVolumeTitanQuotaTemplateFileCountReset
                Unsigned32,
            virtualVolumeTitanQuotaTemplateFileCountWarning
                Unsigned32,
            virtualVolumeTitanQuotaTemplateFileCountCritical
                Unsigned32
        }

    virtualVolumeQuotaTemplateTargetType OBJECT-TYPE
        SYNTAX INTEGER {
            user(1),
            group(2)
        }
        MAX-ACCESS read-only
        STATUS obsolete
        DESCRIPTION
            "The type of a Quota Template associated with a Virtual
            Volume.

            user(1)     - a Quota Template for a user
            group(2)    - a Quota Template for a group.

            This object is now obsolete."
        ::= { virtualVolumeTitanQuotaTemplateEntry 1 }

    virtualVolumeQuotaTemplateIgnoreWellKnownGroups OBJECT-TYPE
        SYNTAX INTEGER {
            ignore(1),
            include(2),
            notapplicable(3)
        }
        MAX-ACCESS read-only
        STATUS obsolete
        DESCRIPTION
            "Should this Quota Template generate a quota for 
            well-known groups. A well-known group would
            be a group to which many or all of the potential
            users belong. It may be desired to ignore such
            a group because a default quota generated would
            quickly reach usage or file-count thresholds, and
            cause events to be logged unnecessarily.

            A value notapplicable(3) will be set if the row in
            the table relates to a User Quota Template.

            This object is now obsolete."
        ::= { virtualVolumeTitanQuotaTemplateEntry 2 }

    virtualVolumeTitanQuotaTemplateUsageLimit OBJECT-TYPE
        SYNTAX Unsigned32 (1..4294967295)
        MAX-ACCESS read-only
        STATUS obsolete
        DESCRIPTION
            "The upper limit set for usage of space in the quota.

            This object is now obsolete."
        ::= { virtualVolumeTitanQuotaTemplateEntry 3 }

    virtualVolumeTitanQuotaTemplateUsageHardLimit OBJECT-TYPE
        SYNTAX INTEGER {
            soft(0),
            hard(1)
        }
        MAX-ACCESS read-only
        STATUS obsolete
        DESCRIPTION
            "Whether the upper limit for usage on the quota is a hard limit.

             soft(1)    - not a hard limit.
             hard(2)    - a hard limit.

            This object is now obsolete."
        ::= { virtualVolumeTitanQuotaTemplateEntry 4 }

    virtualVolumeTitanQuotaTemplateUsageReset OBJECT-TYPE
        SYNTAX Unsigned32 (1..4294967295)
        MAX-ACCESS read-only
        STATUS obsolete
        DESCRIPTION
            "When a warning limit for usage has been reached, a warning event
            will not be logged again until the use of the quota has first
            dropped back to the reset value.

            This object is now obsolete."
        ::= { virtualVolumeTitanQuotaTemplateEntry 5 }

    virtualVolumeTitanQuotaTemplateUsageWarning OBJECT-TYPE
        SYNTAX Unsigned32 (1..4294967295)
        MAX-ACCESS read-only
        STATUS obsolete
        DESCRIPTION
            "A warning event will be logged when the usage of the quota has
            reached this value.

            This object is now obsolete."
        ::= { virtualVolumeTitanQuotaTemplateEntry 6 }

    virtualVolumeTitanQuotaTemplateUsageCritical OBJECT-TYPE
        SYNTAX Unsigned32 (1..4294967295)
        MAX-ACCESS read-only
        STATUS obsolete
        DESCRIPTION
            "A severe event will be logged when the usage of the quota has
            reached this value.

            This object is now obsolete."
        ::= { virtualVolumeTitanQuotaTemplateEntry 7 }

    virtualVolumeTitanQuotaTemplateFileCountLimit OBJECT-TYPE
        SYNTAX Unsigned32 (1..4294967295)
        MAX-ACCESS read-only
        STATUS obsolete
        DESCRIPTION
            "The upper limit set for the number of files in the quota.

            This object is now obsolete."
        ::= { virtualVolumeTitanQuotaTemplateEntry 8 }

    virtualVolumeTitanQuotaTemplateFileCountHardLimit OBJECT-TYPE
        SYNTAX INTEGER {
            soft(0),
            hard(1)
        }
        MAX-ACCESS read-only
        STATUS obsolete
        DESCRIPTION
            "Whether the upper limit for number of files in the quota
            is a hard limit.

             soft(1)    - not a hard limit.
             hard(2)    - a hard limit.

            This object is now obsolete."
        ::= { virtualVolumeTitanQuotaTemplateEntry 9 }

    virtualVolumeTitanQuotaTemplateFileCountReset OBJECT-TYPE
        SYNTAX Unsigned32 (1..4294967295)
        MAX-ACCESS read-only
        STATUS obsolete
        DESCRIPTION
            "When a warning limit for number of files has been reached,
            a warning event will not be logged again until the file count
            in the quota has first dropped back to the reset value.

            This object is now obsolete."
        ::= { virtualVolumeTitanQuotaTemplateEntry 10 }

    virtualVolumeTitanQuotaTemplateFileCountWarning OBJECT-TYPE
        SYNTAX Unsigned32 (1..4294967295)
        MAX-ACCESS read-only
        STATUS obsolete
        DESCRIPTION
            "A warning event will be logged when the file count in the quota has
            reached this value.

            This object is now obsolete."
        ::= { virtualVolumeTitanQuotaTemplateEntry 11 }

    virtualVolumeTitanQuotaTemplateFileCountCritical OBJECT-TYPE
        SYNTAX Unsigned32 (1..4294967295)
        MAX-ACCESS read-only
        STATUS obsolete
        DESCRIPTION
            "A severe event will be logged when the file count in the quota has
            reached this value.

            This object is now obsolete."
        ::= { virtualVolumeTitanQuotaTemplateEntry 12 }

    virtualVolumeTitanQuotaTable OBJECT-TYPE
        SYNTAX SEQUENCE OF VirtualVolumeTitanQuotaEntry
        MAX-ACCESS not-accessible
        STATUS obsolete
        DESCRIPTION
            "A table containing quotas associated with
            Virtual Volumes. The quotas are indexed by the values
            virtualVolumeTitanSpanId and virtualVolumeTitanTarget in
            virtualVolumeTitanTable, and the quota name.

            This object is now obsolete."
        ::= { virtualVolumesTitan 5 }

    virtualVolumeTitanQuotaEntry OBJECT-TYPE
        SYNTAX VirtualVolumeTitanQuotaEntry
        MAX-ACCESS not-accessible
        STATUS obsolete
        DESCRIPTION
            "Information about a quota.

            This object is now obsolete."
        INDEX { virtualVolumeTitanSpanId, virtualVolumeTitanName, virtualVolumeTitanQuotaTarget, virtualVolumeTitanQuotaTargetType }
        ::= { virtualVolumeTitanQuotaTable 1 }

    VirtualVolumeTitanQuotaEntry ::=
        SEQUENCE {
            virtualVolumeTitanQuotaTarget
                DisplayString,
            virtualVolumeTitanQuotaType
                INTEGER,
            virtualVolumeTitanQuotaTargetType
                INTEGER,
            virtualVolumeTitanQuotaUsage
                Unsigned32,
            virtualVolumeTitanQuotaFileCount
                Unsigned32,
            virtualVolumeTitanQuotaUsageLimit
                Unsigned32,
            virtualVolumeTitanQuotaUsageHardLimit
                INTEGER,
            virtualVolumeTitanQuotaUsageReset
                Unsigned32,
            virtualVolumeTitanQuotaUsageWarning
                Unsigned32,
            virtualVolumeTitanQuotaUsageCritical
                Unsigned32,
            virtualVolumeTitanQuotaFileCountLimit
                Unsigned32,
            virtualVolumeTitanQuotaFileCountHardLimit
                INTEGER,
            virtualVolumeTitanQuotaFileCountReset
                Unsigned32,
            virtualVolumeTitanQuotaFileCountWarning
                Unsigned32,
            virtualVolumeTitanQuotaFileCountCritical
                Unsigned32
        }

    virtualVolumeTitanQuotaTarget OBJECT-TYPE
        SYNTAX DisplayString
        MAX-ACCESS read-only
        STATUS obsolete
        DESCRIPTION
            "The target of a quota.
            If the quota is a Virtual Volume quota (i.e. tracking
            usage of the entire Virtual Volume, regardless of the
            user of group) then the target will be 'Virtual Volume
            Quota'.
            A User Quota will have a target comprised of the user's
            domain and user name, in the form <domain>\<user>.
            A Group quota target will consist of the group's domain
            and group name, in the form <domain>\<group>.

            This object is now obsolete."
        ::= { virtualVolumeTitanQuotaEntry 1 }

    virtualVolumeTitanQuotaType OBJECT-TYPE
        SYNTAX INTEGER {
            default(1),
            explicit(2)
        }
        MAX-ACCESS read-only
        STATUS obsolete
        DESCRIPTION
            "Indicates whether the quota is a default or explicit quota.

             default(1)  - the quota has been created automatically using
                            the default values for the Virtual Volume.
             explicit(2) - the quota has been created explicitly using
                            user-defined values.

            This object is now obsolete."
        ::= { virtualVolumeTitanQuotaEntry 2 }

    virtualVolumeTitanQuotaTargetType OBJECT-TYPE
        SYNTAX INTEGER {
            user(1),
            group(2),
            virtualvolume(3)
        }
        MAX-ACCESS read-only
        STATUS obsolete
        DESCRIPTION
            "Indicates whether the scope of the quota's tracking.

             user(1)            - the quota is tracking a single user's use
                                  of the Virtual Volume.
             group(2)           - the quota is tracking a group's use of the
                                  Virtual Volume.
             virtualvolume(3)   - the quota is tracking the use of the entire
                                  Virtual Volume.

            This object is now obsolete."
        ::= { virtualVolumeTitanQuotaEntry 3 }

    virtualVolumeTitanQuotaUsage OBJECT-TYPE
        SYNTAX Unsigned32 (1..4294967295)
        MAX-ACCESS read-only
        STATUS obsolete
        DESCRIPTION
            "The usage of this quota, in bytes.

            This object is now obsolete."
        ::= { virtualVolumeTitanQuotaEntry 4 }

    virtualVolumeTitanQuotaFileCount OBJECT-TYPE
        SYNTAX Unsigned32 (1..4294967295)
        MAX-ACCESS read-only
        STATUS obsolete
        DESCRIPTION
            "The usage of this quota, in number of files.

            This object is now obsolete."
        ::= { virtualVolumeTitanQuotaEntry 5 }

    virtualVolumeTitanQuotaUsageLimit OBJECT-TYPE
        SYNTAX Unsigned32 (1..4294967295)
        MAX-ACCESS read-only
        STATUS obsolete
        DESCRIPTION
            "The upper limit set for usage of space in this quota.

            This object is now obsolete."
        ::= { virtualVolumeTitanQuotaEntry 6 }

    virtualVolumeTitanQuotaUsageHardLimit OBJECT-TYPE
        SYNTAX INTEGER {
            soft(0),
            hard(1),
            unknown(3)
        }
        MAX-ACCESS read-only
        STATUS obsolete
        DESCRIPTION
            "Whether the upper limit for usage on this quota is a hard limit.

             soft(1)    - not a hard limit.
             hard(2)    - a hard limit.

            This object is now obsolete."
        ::= { virtualVolumeTitanQuotaEntry 7 }

    virtualVolumeTitanQuotaUsageReset OBJECT-TYPE
        SYNTAX Unsigned32 (1..4294967295)
        MAX-ACCESS read-only
        STATUS obsolete
        DESCRIPTION
            "When a warning limit for usage has been reached, a warning event
            will not be logged again until the use of the quota has first
            dropped back to the reset value.

            This object is now obsolete."
        ::= { virtualVolumeTitanQuotaEntry 8 }

    virtualVolumeTitanQuotaUsageWarning OBJECT-TYPE
        SYNTAX Unsigned32 (1..4294967295)
        MAX-ACCESS read-only
        STATUS obsolete
        DESCRIPTION
            "A warning event will be logged when the usage of a quota has
            reached this value.

            This object is now obsolete."
        ::= { virtualVolumeTitanQuotaEntry 9 }

    virtualVolumeTitanQuotaUsageCritical OBJECT-TYPE
        SYNTAX Unsigned32 (1..4294967295)
        MAX-ACCESS read-only
        STATUS obsolete
        DESCRIPTION
            "A severe event will be logged when the usage of a quota has
            reached this value.

            This object is now obsolete."
        ::= { virtualVolumeTitanQuotaEntry 10 }

    virtualVolumeTitanQuotaFileCountLimit OBJECT-TYPE
        SYNTAX Unsigned32 (1..4294967295)
        MAX-ACCESS read-only
        STATUS obsolete
        DESCRIPTION
            "The upper limit set for the number of files in a quota.

            This object is now obsolete."
        ::= { virtualVolumeTitanQuotaEntry 11 }

    virtualVolumeTitanQuotaFileCountHardLimit OBJECT-TYPE
        SYNTAX INTEGER {
            soft(0),
            hard(1),
            unknown(2)
        }
        MAX-ACCESS read-only
        STATUS obsolete
        DESCRIPTION
            "Whether the upper limit for number of files in a quota
            is a hard limit.

             soft(1)    - not a hard limit.
             hard(2)    - a hard limit.

            This object is now obsolete."
        ::= { virtualVolumeTitanQuotaEntry 12 }

    virtualVolumeTitanQuotaFileCountReset OBJECT-TYPE
        SYNTAX Unsigned32 (1..4294967295)
        MAX-ACCESS read-only
        STATUS obsolete
        DESCRIPTION
            "When a warning limit for number of files has been reached,
            a warning event will not be logged again until the file count
            in a quota has first dropped back to the reset value.

            This object is now obsolete."
        ::= { virtualVolumeTitanQuotaEntry 13 }

    virtualVolumeTitanQuotaFileCountWarning OBJECT-TYPE
        SYNTAX Unsigned32 (1..4294967295)
        MAX-ACCESS read-only
        STATUS obsolete
        DESCRIPTION
            "A warning event will be logged when the file count in a quota has
            reached this value.

            This object is now obsolete."
        ::= { virtualVolumeTitanQuotaEntry 14 }

    virtualVolumeTitanQuotaFileCountCritical OBJECT-TYPE
        SYNTAX Unsigned32 (1..4294967295)
        MAX-ACCESS read-only
        STATUS obsolete
        DESCRIPTION
            "A severe event will be logged when the file count in a quota has
            reached this value.

            This object is now obsolete."
        ::= { virtualVolumeTitanQuotaEntry 15 }

    virtualVolumeTitanQuotaDefaultTable OBJECT-TYPE
        SYNTAX SEQUENCE OF VirtualVolumeTitanQuotaDefaultEntry
        MAX-ACCESS not-accessible
        STATUS current
        DESCRIPTION
            "A table containing quota templates (defaults) associated with
            Virtual Volumes. The template is indexed by the values
            virtualVolumeTitanSpanId and virtualVolumeTitanTarget in
            virtualVolumeTitanTable, and the
            virtualVolumeQuotaDefaultTargetType.

            The two types of quota template are: user quota template,
            and group quota template. The templates define the
            default quota settings which will be used to create a
            Default Quota when a user or group begins to use the Virtual
            Volume. Once the default quota has been created, a user
            or group's quota may be modified, when it will become an
            Explicit Quota."
        ::= { virtualVolumesTitan 6 }

    virtualVolumeTitanQuotaDefaultEntry OBJECT-TYPE
        SYNTAX VirtualVolumeTitanQuotaDefaultEntry
        MAX-ACCESS not-accessible
        STATUS current
        DESCRIPTION
            "A quota template (default) associated with a Virtual Volume.
            The template is indexed by the values virtualVolumeTitanSpanId
            and virtualVolumeTitanTarget in virtualVolumeTitanTable, and
            the virtualVolumeQuotaDefaultTargetType."
        INDEX { virtualVolumeTitanSpanId, virtualVolumeTitanName, virtualVolumeQuotaDefaultTargetType }
        ::= { virtualVolumeTitanQuotaDefaultTable 1 }

    VirtualVolumeTitanQuotaDefaultEntry ::=
        SEQUENCE {
            virtualVolumeQuotaDefaultTargetType
                INTEGER,
            virtualVolumeQuotaDefaultIgnoreWellKnownGroups
                INTEGER,
            virtualVolumeTitanQuotaDefaultUsageLimit
                Counter64,
            virtualVolumeTitanQuotaDefaultUsageHardLimit
                INTEGER,
            virtualVolumeTitanQuotaDefaultUsageReset
                Counter64,
            virtualVolumeTitanQuotaDefaultUsageWarning
                Counter64,
            virtualVolumeTitanQuotaDefaultUsageCritical
                Counter64,
            virtualVolumeTitanQuotaDefaultFileCountLimit
                Unsigned32,
            virtualVolumeTitanQuotaDefaultFileCountHardLimit
                INTEGER,
            virtualVolumeTitanQuotaDefaultFileCountReset
                Unsigned32,
            virtualVolumeTitanQuotaDefaultFileCountWarning
                Unsigned32,
            virtualVolumeTitanQuotaDefaultFileCountCritical
                Unsigned32
        }

    virtualVolumeQuotaDefaultTargetType OBJECT-TYPE
        SYNTAX INTEGER {
            user(1),
            group(2)
        }
        MAX-ACCESS read-only
        STATUS current
        DESCRIPTION
            "The type of a Quota Template (default) associated with a
            Virtual Volume.

            user(1)     - a Quota Template for a user
            group(2)    - a Quota Template for a group."
        ::= { virtualVolumeTitanQuotaDefaultEntry 1 }

    virtualVolumeQuotaDefaultIgnoreWellKnownGroups OBJECT-TYPE
        SYNTAX INTEGER {
            ignore(1),
            include(2),
            notapplicable(3)
        }
        MAX-ACCESS read-only
        STATUS current
        DESCRIPTION
            "Should this Quota Template (default) generate a quota for
            well-known groups. A well-known group would
            be a group to which many or all of the potential
            users belong. It may be desired to ignore such
            a group because a default quota generated would
            quickly reach usage or file-count thresholds, and
            cause events to be logged unnecessarily.

            A value notapplicable(3) will be set if the row in
            the table relates to a User Quota Template."
        ::= { virtualVolumeTitanQuotaDefaultEntry 2 }

    virtualVolumeTitanQuotaDefaultUsageLimit OBJECT-TYPE
        SYNTAX Counter64
        MAX-ACCESS read-only
        STATUS current
        DESCRIPTION
            "The upper limit set for usage of space in the quota."
        ::= { virtualVolumeTitanQuotaDefaultEntry 3 }

    virtualVolumeTitanQuotaDefaultUsageHardLimit OBJECT-TYPE
        SYNTAX INTEGER {
            soft(0),
            hard(1),
            unknown(2)
        }
        MAX-ACCESS read-only
        STATUS current
        DESCRIPTION
            "Whether the upper limit for usage on the quota is a hard limit.

             soft(1)    - not a hard limit.
             hard(2)    - a hard limit."
        ::= { virtualVolumeTitanQuotaDefaultEntry 4 }

    virtualVolumeTitanQuotaDefaultUsageReset OBJECT-TYPE
        SYNTAX Counter64
        MAX-ACCESS read-only
        STATUS current
        DESCRIPTION
            "When a warning limit for usage has been reached, a warning event
            will not be logged again until the use of the quota has first
            dropped back to the reset value."
        ::= { virtualVolumeTitanQuotaDefaultEntry 5 }

    virtualVolumeTitanQuotaDefaultUsageWarning OBJECT-TYPE
        SYNTAX Counter64
        MAX-ACCESS read-only
        STATUS current
        DESCRIPTION
            "A warning event will be logged when the usage of the quota has
            reached this value."
        ::= { virtualVolumeTitanQuotaDefaultEntry 6 }

    virtualVolumeTitanQuotaDefaultUsageCritical OBJECT-TYPE
        SYNTAX Counter64
        MAX-ACCESS read-only
        STATUS current
        DESCRIPTION
            "A severe event will be logged when the usage of the quota has
            reached this value."
        ::= { virtualVolumeTitanQuotaDefaultEntry 7 }

    virtualVolumeTitanQuotaDefaultFileCountLimit OBJECT-TYPE
        SYNTAX Unsigned32 (1..4294967295)
        MAX-ACCESS read-only
        STATUS current
        DESCRIPTION
            "The upper limit set for the number of files in the quota."
        ::= { virtualVolumeTitanQuotaDefaultEntry 8 }

    virtualVolumeTitanQuotaDefaultFileCountHardLimit OBJECT-TYPE
        SYNTAX INTEGER {
            soft(0),
            hard(1),
            unknown(2)
        }
        MAX-ACCESS read-only
        STATUS current
        DESCRIPTION
            "Whether the upper limit for number of files in the quota
            is a hard limit.

             soft(1)    - not a hard limit.
             hard(2)    - a hard limit."
        ::= { virtualVolumeTitanQuotaDefaultEntry 9 }

    virtualVolumeTitanQuotaDefaultFileCountReset OBJECT-TYPE
        SYNTAX Unsigned32 (1..4294967295)
        MAX-ACCESS read-only
        STATUS current
        DESCRIPTION
            "When a warning limit for number of files has been reached,
            a warning event will not be logged again until the file count
            in the quota has first dropped back to the reset value."
        ::= { virtualVolumeTitanQuotaDefaultEntry 10 }

    virtualVolumeTitanQuotaDefaultFileCountWarning OBJECT-TYPE
        SYNTAX Unsigned32 (1..4294967295)
        MAX-ACCESS read-only
        STATUS current
        DESCRIPTION
            "A warning event will be logged when the file count in the quota has
            reached this value."
        ::= { virtualVolumeTitanQuotaDefaultEntry 11 }

    virtualVolumeTitanQuotaDefaultFileCountCritical OBJECT-TYPE
        SYNTAX Unsigned32 (1..4294967295)
        MAX-ACCESS read-only
        STATUS current
        DESCRIPTION
            "A severe event will be logged when the file count in the quota has
            reached this value."
        ::= { virtualVolumeTitanQuotaDefaultEntry 12 }

    virtualVolumeTitanQuotasTable OBJECT-TYPE
        SYNTAX SEQUENCE OF VirtualVolumeTitanQuotasEntry
        MAX-ACCESS not-accessible
        STATUS current
        DESCRIPTION
            "A table containing quotas associated with
            Virtual Volumes. The quotas are indexed by the values
            virtualVolumeTitanSpanId and virtualVolumeTitanTarget in
            virtualVolumeTitanTable, and the quota name."
        ::= { virtualVolumesTitan 7 }

    virtualVolumeTitanQuotasEntry OBJECT-TYPE
        SYNTAX VirtualVolumeTitanQuotasEntry
        MAX-ACCESS not-accessible
        STATUS current
        DESCRIPTION
            "Information about a quota."
        INDEX { virtualVolumeTitanSpanId, virtualVolumeTitanName, virtualVolumeTitanQuotasTarget, virtualVolumeTitanQuotasTargetType }
        ::= { virtualVolumeTitanQuotasTable 1 }

    VirtualVolumeTitanQuotasEntry ::=
        SEQUENCE {
            virtualVolumeTitanQuotasTarget
                DisplayString,
            virtualVolumeTitanQuotasType
                INTEGER,
            virtualVolumeTitanQuotasTargetType
                INTEGER,
            virtualVolumeTitanQuotasUsage
                Counter64,
            virtualVolumeTitanQuotasFileCount
                Unsigned32,
            virtualVolumeTitanQuotasUsageLimit
                Counter64,
            virtualVolumeTitanQuotasUsageHardLimit
                INTEGER,
            virtualVolumeTitanQuotasUsageReset
                Counter64,
            virtualVolumeTitanQuotasUsageWarning
                Counter64,
            virtualVolumeTitanQuotasUsageCritical
                Counter64,
            virtualVolumeTitanQuotasFileCountLimit
                Unsigned32,
            virtualVolumeTitanQuotasFileCountHardLimit
                INTEGER,
            virtualVolumeTitanQuotasFileCountReset
                Unsigned32,
            virtualVolumeTitanQuotasFileCountWarning
                Unsigned32,
            virtualVolumeTitanQuotasFileCountCritical
                Unsigned32
        }

    virtualVolumeTitanQuotasTarget OBJECT-TYPE
        SYNTAX DisplayString
        MAX-ACCESS read-only
        STATUS current
        DESCRIPTION
            "The target of a quota.
            If the quota is a Virtual Volume quota (i.e. tracking
            usage of the entire Virtual Volume, regardless of the
            user of group) then the target will be 'Virtual Volume
            Quota'.
            A User Quota will have a target comprised of the user's
            domain and user name, in the form <domain>\<user>.
            A Group quota target will consist of the group's domain
            and group name, in the form <domain>\<group>."


        ::= { virtualVolumeTitanQuotasEntry 1 }

    virtualVolumeTitanQuotasType OBJECT-TYPE
        SYNTAX INTEGER {
            default(1),
            explicit(2),
            unknown(3)
        }
        MAX-ACCESS read-only
        STATUS current
        DESCRIPTION
            "Indicates whether the quota is a default or explicit quota.

             default(1)  - the quota has been created automatically using
                            the default values for the Virtual Volume.
             explicit(2) - the quota has been created explicitly using
                            user-defined values."
        ::= { virtualVolumeTitanQuotasEntry 2 }

    virtualVolumeTitanQuotasTargetType OBJECT-TYPE
        SYNTAX INTEGER {
            user(1),
            group(2),
            virtualvolume(3),
            unknown(4)
        }
        MAX-ACCESS read-only
        STATUS current
        DESCRIPTION
            "Indicates whether the scope of the quota's tracking.

             user(1)            - the quota is tracking a single user's use
                                  of the Virtual Volume.
             group(2)           - the quota is tracking a group's use of the
                                  Virtual Volume.
             virtualvolume(3)   - the quota is tracking the use of the entire
                                  Virtual Volume."
        ::= { virtualVolumeTitanQuotasEntry 3 }

    virtualVolumeTitanQuotasUsage OBJECT-TYPE
        SYNTAX Counter64
        MAX-ACCESS read-only
        STATUS current
        DESCRIPTION
            "The usage of this quota, in bytes."
        ::= { virtualVolumeTitanQuotasEntry 4 }

    virtualVolumeTitanQuotasFileCount OBJECT-TYPE
        SYNTAX Unsigned32 (1..4294967295)
        MAX-ACCESS read-only
        STATUS current
        DESCRIPTION
            "The usage of this quota, in number of files."
        ::= { virtualVolumeTitanQuotasEntry 5 }

    virtualVolumeTitanQuotasUsageLimit OBJECT-TYPE
        SYNTAX Counter64
        MAX-ACCESS read-only
        STATUS current
        DESCRIPTION
            "The upper limit set for usage of space in this quota."
        ::= { virtualVolumeTitanQuotasEntry 6 }

    virtualVolumeTitanQuotasUsageHardLimit OBJECT-TYPE
        SYNTAX INTEGER {
            soft(0),
            hard(1),
            unknown(2)
        }
        MAX-ACCESS read-only
        STATUS current
        DESCRIPTION
            "Whether the upper limit for usage on this quota is a hard limit.

             soft(1)    - not a hard limit.
             hard(2)    - a hard limit."
        ::= { virtualVolumeTitanQuotasEntry 7 }

    virtualVolumeTitanQuotasUsageReset OBJECT-TYPE
        SYNTAX Counter64
        MAX-ACCESS read-only
        STATUS current
        DESCRIPTION
            "When a warning limit for usage has been reached, a warning event
            will not be logged again until the use of the quota has first
            dropped back to the reset value."
        ::= { virtualVolumeTitanQuotasEntry 8 }

    virtualVolumeTitanQuotasUsageWarning OBJECT-TYPE
        SYNTAX Counter64
        MAX-ACCESS read-only
        STATUS current
        DESCRIPTION
            "A warning event will be logged when the usage of a quota has
            reached this value."
        ::= { virtualVolumeTitanQuotasEntry 9 }

    virtualVolumeTitanQuotasUsageCritical OBJECT-TYPE
        SYNTAX Counter64
        MAX-ACCESS read-only
        STATUS current
        DESCRIPTION
            "A severe event will be logged when the usage of a quota has
            reached this value."
        ::= { virtualVolumeTitanQuotasEntry 10 }

    virtualVolumeTitanQuotasFileCountLimit OBJECT-TYPE
        SYNTAX Unsigned32 (1..4294967295)
        MAX-ACCESS read-only
        STATUS current
        DESCRIPTION
            "The upper limit set for the number of files in a quota."
        ::= { virtualVolumeTitanQuotasEntry 11 }

    virtualVolumeTitanQuotasFileCountHardLimit OBJECT-TYPE
        SYNTAX INTEGER {
            soft(0),
            hard(1),
            unknown(2)
        }
        MAX-ACCESS read-only
        STATUS current
        DESCRIPTION
            "Whether the upper limit for number of files in a quota
            is a hard limit.

             soft(1)    - not a hard limit.
             hard(2)    - a hard limit."
        ::= { virtualVolumeTitanQuotasEntry 12 }

    virtualVolumeTitanQuotasFileCountReset OBJECT-TYPE
        SYNTAX Unsigned32 (1..4294967295)
        MAX-ACCESS read-only
        STATUS current
        DESCRIPTION
            "When a warning limit for number of files has been reached,
            a warning event will not be logged again until the file count
            in a quota has first dropped back to the reset value."
        ::= { virtualVolumeTitanQuotasEntry 13 }

    virtualVolumeTitanQuotasFileCountWarning OBJECT-TYPE
        SYNTAX Unsigned32 (1..4294967295)
        MAX-ACCESS read-only
        STATUS current
        DESCRIPTION
            "A warning event will be logged when the file count in a quota has
            reached this value."
        ::= { virtualVolumeTitanQuotasEntry 14 }

    virtualVolumeTitanQuotasFileCountCritical OBJECT-TYPE
        SYNTAX Unsigned32 (1..4294967295)
        MAX-ACCESS read-only
        STATUS current
        DESCRIPTION
            "A severe event will be logged when the file count in a quota has
            reached this value."
        ::= { virtualVolumeTitanQuotasEntry 15 }

--------------------------------------------------------------------------------
--
-- StorageTitan / NVRAM
--
--------------------------------------------------------------------------------

    nvramSize OBJECT-TYPE
        SYNTAX Unsigned32 (1..2147483647)
        MAX-ACCESS read-only
        STATUS obsolete
        DESCRIPTION
            "The total size of nvram. If no formatted or mounted volume
            is found, or if nvram is not supported, this value will be reported
            as zero.

            This object is obsolete, and is re-implemented in nvramPoolTable."
        ::= { nvram 1 }

    nvramMaximumUsed OBJECT-TYPE
        SYNTAX Unsigned32 (1..2147483647)
        MAX-ACCESS read-only
        STATUS obsolete
        DESCRIPTION
            "The maximum amount of nvram used. If no formatted or mounted volume
            is found, or if nvram is not supported, this value will be reported
            as zero.

            This object is obsolete, and is re-implemented in nvramPoolTable."
        ::= { nvram 2 }

    nvramTotalCurrentUsage OBJECT-TYPE
        SYNTAX Unsigned32 (1..2147483647)
        MAX-ACCESS read-only
        STATUS obsolete
        DESCRIPTION
            "The amount of nvram currently in use. If no formatted or mounted
            volume is found, or if nvram is not supported, this value will be
            reported as zero.

            This object is obsolete, and is re-implemented in nvramPoolTable."
        ::= { nvram 3 }

    nvramNumber OBJECT-TYPE
        SYNTAX Unsigned32 (1..2147483647)
        MAX-ACCESS read-only
        STATUS obsolete
        DESCRIPTION
            "The number of volumes with NVRAM statistics."
        ::= { nvram 4 }

    nvramTable OBJECT-TYPE
        SYNTAX SEQUENCE OF NvramEntry
        MAX-ACCESS not-accessible
        STATUS obsolete
        DESCRIPTION
            "A table of NVRAM data for a given volume."
        ::= { nvram 5 }

    nvramEntry OBJECT-TYPE
        SYNTAX NvramEntry
        MAX-ACCESS not-accessible
        STATUS obsolete
        DESCRIPTION
            "Information about NVRAM on a given volume. The
            volume must be formatted, mounted, and NVRAM must
            be supported."
        INDEX { spanId }
        ::= { nvramTable 1 }

    NvramEntry ::=
        SEQUENCE {
            spanId
                Unsigned32,
            nvramCurrentUsage
                Unsigned32,
            nvramNumberCheckpoints
                Unsigned32,
            nvramNumberActivityCheckpoints
                Unsigned32
        }

    spanId OBJECT-TYPE
        SYNTAX Unsigned32
        MAX-ACCESS read-only
        STATUS obsolete
        DESCRIPTION
            "The id of the Span hosting the volume with which the
            NVRAM is associated."
        ::= { nvramEntry 1 }

    nvramCurrentUsage OBJECT-TYPE
        SYNTAX Unsigned32
        MAX-ACCESS read-only
        STATUS obsolete
        DESCRIPTION
            "The amount of NVRAM currently in use for this volume."
        ::= { nvramEntry 2 }

   nvramNumberCheckpoints OBJECT-TYPE
        SYNTAX Unsigned32
        MAX-ACCESS read-only
        STATUS obsolete
        DESCRIPTION
            "The total number of checkpoints which have occurred for the
            NVRAM assigned to this volume."
        ::= { nvramEntry 3 }

   nvramNumberActivityCheckpoints OBJECT-TYPE
        SYNTAX Unsigned32
        MAX-ACCESS read-only
        STATUS obsolete
        DESCRIPTION
            "The number of checkpoints which have occurred for the NVRAM
            assigned to this volume as a result of file system activity
            (i.e. not timed checkpoints."
        ::= { nvramEntry 4 } 
        
   nvramPoolTable OBJECT-TYPE
        SYNTAX SEQUENCE OF NvramPoolEntry
        MAX-ACCESS not-accessible
        STATUS obsolete
        DESCRIPTION
            "A table of NVRAM data for a given Cluster Node."
        ::= { nvram 6 }

    nvramPoolEntry OBJECT-TYPE
        SYNTAX NvramPoolEntry
        MAX-ACCESS not-accessible
        STATUS obsolete
        DESCRIPTION
            "Information about NVRAM on a given Cluster Node."
        INDEX { clusterNodeId }
        ::= { nvramPoolTable 1 }

    NvramPoolEntry ::=
        SEQUENCE {
            clusterNodeId
                Unsigned32,
            nvramPoolSize
                Unsigned32,
            nvramPoolMaximumUsed
                Unsigned32,
            nvramPoolTotalCurrentUsage
                Unsigned32
        }

    clusterNodeId OBJECT-TYPE
        SYNTAX Unsigned32 (0..255)
        MAX-ACCESS read-only
        STATUS obsolete
        DESCRIPTION
            "The ID of the cluster node for which these pool
            statistics are reported."
        ::= { nvramPoolEntry 1 }

    nvramPoolSize OBJECT-TYPE
        SYNTAX Unsigned32 (1..2147483647)
        MAX-ACCESS read-only
        STATUS obsolete
        DESCRIPTION
            "The total size of nvram. If no formatted or mounted volume
            is found, or if nvram is not supported, this value will be reported
            as zero."
        ::= { nvramPoolEntry 2 }

    nvramPoolMaximumUsed OBJECT-TYPE
        SYNTAX Unsigned32 (1..2147483647)
        MAX-ACCESS read-only
        STATUS obsolete
        DESCRIPTION
            "The maximum amount of nvram used. If no formatted or mounted volume
            is found, or if nvram is not supported, this value will be reported
            as zero."
        ::= { nvramPoolEntry 3 }

    nvramPoolTotalCurrentUsage OBJECT-TYPE
        SYNTAX Unsigned32 (1..2147483647)
        MAX-ACCESS read-only
        STATUS obsolete
        DESCRIPTION
            "The amount of nvram currently in use. If no formatted or mounted
            volume is found, or if nvram is not supported, this value will be
            reported as zero."
        ::= { nvramPoolEntry 4 }

--------------------------------------------------------------------------------
--
-- Network / Ethernet / LinkAggregation
--
--------------------------------------------------------------------------------

    lagNumber OBJECT-TYPE
        SYNTAX Integer32 (1..32)
        MAX-ACCESS read-only
        STATUS current
        DESCRIPTION
            "The number of link aggregation which may be
            configured on each Cluster Node of a system."
        ::= { linkAggregation 1 }

    lagTable OBJECT-TYPE
        SYNTAX SEQUENCE OF LagEntry
        MAX-ACCESS not-accessible
        STATUS current
        DESCRIPTION
            "A table of information about link aggregations
            configured."
        ::= { linkAggregation 2 }

    lagEntry OBJECT-TYPE
        SYNTAX LagEntry
        MAX-ACCESS not-accessible
        STATUS current
        DESCRIPTION
            "Information about link aggregations."
        INDEX { lagName }
        ::= { lagTable 1 }

    LagEntry ::=
        SEQUENCE {
            lagName
                DisplayString,
            linkedInterfaces
                DisplayString
        }

    lagName OBJECT-TYPE
        SYNTAX DisplayString
        MAX-ACCESS read-only
        STATUS current
        DESCRIPTION
            "The name of the Link Aggregation."
        ::= { lagEntry 1 }

    linkedInterfaces OBJECT-TYPE
        SYNTAX DisplayString
        MAX-ACCESS read-only
        STATUS current
        DESCRIPTION
            "A list of physical interfaces in the Link Aggregation."
        ::= { lagEntry 2 }


--------------------------------------------------------------------------------
--
-- MgmntTitan / Packages
--
--------------------------------------------------------------------------------

     packageNumber OBJECT-TYPE
        SYNTAX Integer32 (1..2147483647)
        MAX-ACCESS read-only
        STATUS obsolete
        DESCRIPTION
            "The number of packages in flash.
            
             This object is obsolete. It has not
             been replaced with an alternative."
        ::= { packageMgmnt 1 }

     packageTable OBJECT-TYPE
        SYNTAX SEQUENCE OF PackageEntry
        MAX-ACCESS not-accessible
        STATUS obsolete
        DESCRIPTION
            "A table containing details of the packages available in flash.
            
             This object is obsolete. It has not
             been replaced with an alternative."
        ::= { packageMgmnt 2 }

    packageEntry OBJECT-TYPE
        SYNTAX PackageEntry
        MAX-ACCESS not-accessible
        STATUS obsolete
        DESCRIPTION
            "Information about the packages in flash.
            
             This object is obsolete. It has not
             been replaced with an alternative."
        INDEX { packageName }
        ::= { packageTable 1 }

    PackageEntry ::=
        SEQUENCE {
            packageName
                DisplayString,
            packageDate
                DisplayString,
            packageSize
                Unsigned32,
            packageDefault
                INTEGER,
            packageCurrent
                INTEGER
        }

    packageName OBJECT-TYPE
        SYNTAX DisplayString
        MAX-ACCESS read-only
        STATUS obsolete
        DESCRIPTION
            "The name of the package.
            
             This object is obsolete. It has not
             been replaced with an alternative."
        ::= { packageEntry 1 }

    packageDate OBJECT-TYPE
        SYNTAX DisplayString
        MAX-ACCESS read-only
        STATUS obsolete
        DESCRIPTION
            "The date on which the package was uploaded.
            
             This object is obsolete. It has not
             been replaced with an alternative."
        ::= { packageEntry 2 }

    packageSize OBJECT-TYPE
        SYNTAX Unsigned32 (1..4294967295)
        MAX-ACCESS read-only
        STATUS obsolete
        DESCRIPTION
            "The size of the package in bytes.
            
             This object is obsolete. It has not
             been replaced with an alternative."
        ::= { packageEntry 3 }

    packageDefault OBJECT-TYPE
        SYNTAX INTEGER {
            default(0),
            notdefault(1)
        }
        MAX-ACCESS read-only
        STATUS obsolete
        DESCRIPTION
            "Whether the package is the default package. The default
            package is the package which will be loaded when the server
            is rebooted.
             default(1)    - the default package.
             notdefault(2) - not the default package.
            
             This object is obsolete. It has not
             been replaced with an alternative."
        ::= { packageEntry 4 }

    packageCurrent OBJECT-TYPE
        SYNTAX INTEGER {
            current(0),
            notcurrent(1)
        }
        MAX-ACCESS read-only
        STATUS obsolete
        DESCRIPTION
            "Whether the package is the current package. The current
            package is the package which was loaded when the server
            was rebooted.
             current(1)    - the current package.
             notcurrent(2) - not the current package.
            
             This object is obsolete. It has not
             been replaced with an alternative."
        ::= { packageEntry 5 }

    packageFreeSpace OBJECT-TYPE
        SYNTAX Unsigned32 (1..4294967295)
        MAX-ACCESS read-only
        STATUS obsolete
        DESCRIPTION
            "The amount of available flash file-space, in bytes.
            
             This object is obsolete. It has not
             been replaced with an alternative."
        ::= { packageMgmnt 3 }

--------------------------------------------------------------------------------
--
-- File Protocol Titan / FTP config
--
--------------------------------------------------------------------------------

    ftpConfigServiceEnabled OBJECT-TYPE
        SYNTAX INTEGER {
            enabled(1),
            disabled(2),
            unknown(3)
        }
        MAX-ACCESS read-only
        STATUS obsolete
        DESCRIPTION
            "Indicates whether the FTP service is enabled.

            enabled(1) - the service is enabled
            disabled(2) - the service is disabled
            unknown(3) - the status of the service cannot be
                         determined.

            This object is now obsolete."
        ::= { ftpConfig 1 }

    ftpConfigServiceMaxUsers OBJECT-TYPE
        SYNTAX Unsigned32
        MAX-ACCESS read-only
        STATUS obsolete
        DESCRIPTION
            "The maximum number of FTP users the service will allow.

            This object is now obsolete."
        ::= { ftpConfig 2 }

    ftpConfigTimeout OBJECT-TYPE
        SYNTAX Integer32
        MAX-ACCESS read-only
        STATUS obsolete
        DESCRIPTION
            "The FTP session timeout in minutes.
             NOTE: this value applies to all FTP sessions.

            This object is now obsolete."
        ::= { ftpConfig 3 }

    ftpConfigNTPasswordEnabled OBJECT-TYPE
        SYNTAX INTEGER {
            enabled(1),
            disabled(2),
            notavailable(3),
            unknown(4)
        }
        MAX-ACCESS read-only
        STATUS obsolete
        DESCRIPTION
            "Indicates whether FTP uses NT password authentication.

            enabled(1) - NT security is enabled
            disabled(2) - NT security is disabled
            notavailable(3) - NT security is not available
            unknown(4) - the status of NT security cannot be
                         determined.

            This object is now obsolete."
        ::= { ftpConfig 4 }

    ftpConfigNISPasswordEnabled OBJECT-TYPE
        SYNTAX INTEGER {
            enabled(1),
            disabled(2),
            notavailable(3),
            unknown(4)
        }
        MAX-ACCESS read-only
        STATUS obsolete
        DESCRIPTION
            "Indicates whether FTP uses NIS password authentication.

            enabled(1) - NIS security is enabled
            disabled(2) - NIS security is disabled
            notavailable(3) - NIS security is not available
            unknown(4) - the status of NIS security cannot be
                         determined.

            This object is now obsolete."
        ::= { ftpConfig 5 }

    ftpAuditLoggingTable OBJECT-TYPE
        SYNTAX SEQUENCE OF FtpAuditLoggingEntry
        MAX-ACCESS not-accessible
        STATUS obsolete
        DESCRIPTION
            "A table containing the FTP audit logging configuration 
            for the system.

             The number of entries in this table is given by the number of
             EVSs.

            This object is now obsolete."
        ::= { ftpConfig 6 }

    ftpAuditLoggingEntry OBJECT-TYPE
        SYNTAX FtpAuditLoggingEntry
        MAX-ACCESS not-accessible
        STATUS obsolete
        DESCRIPTION
            "FTP audit logging information."
        INDEX { ftpAuditLoggingEVS }
        ::= { ftpAuditLoggingTable 1 }

    FtpAuditLoggingEntry ::=
        SEQUENCE {
            ftpAuditLoggingEVS
                Integer32,
            ftpConfigAuditLogging
                INTEGER,
            ftpConfigAuditLogDeviceId
                Integer32,
            ftpConfigAuditLogDirectory
                DisplayString,
            ftpConfigAuditLogRecordsPerFile
                Unsigned32,
            ftpConfigAuditMaximumLogFiles
                Unsigned32
        }

    ftpAuditLoggingEVS OBJECT-TYPE
        SYNTAX Integer32 (0..255)
        MAX-ACCESS read-only
        STATUS obsolete
        DESCRIPTION
            "The ID of the EVS the FTP audit logging
             configuration is associated with.

            This object is now obsolete."
        ::= { ftpAuditLoggingEntry 1 }

    ftpConfigAuditLogging OBJECT-TYPE
        SYNTAX INTEGER {
            enabled(1),
            disabled(2),
            unknown(3)
        }
        MAX-ACCESS read-only
        STATUS obsolete
        DESCRIPTION
            "Indicates whether FTP Audit logging is enabled on
            this Cluster Node.

            enabled(1) - logging is enabled
            disabled(2) - logging is disabled
            unknown(3) - the status of logging cannot be
                         determined.

            This object is now obsolete."
        ::= { ftpAuditLoggingEntry 2 }

    ftpConfigAuditLogDeviceId OBJECT-TYPE
        SYNTAX Integer32
        MAX-ACCESS read-only
        STATUS obsolete
        DESCRIPTION
            "The Device ID of the volume to which the FTP server
            is to write the audit log.

            This object is now obsolete."
        ::= { ftpAuditLoggingEntry 3 }

    ftpConfigAuditLogDirectory OBJECT-TYPE
        SYNTAX DisplayString
        MAX-ACCESS read-only
        STATUS obsolete
        DESCRIPTION
            "The directory to which the FTP server is to write
            the audit log.

            This object is now obsolete."
        ::= { ftpAuditLoggingEntry 4 }

    ftpConfigAuditLogRecordsPerFile OBJECT-TYPE
        SYNTAX Unsigned32
        MAX-ACCESS read-only
        STATUS obsolete
        DESCRIPTION
            "The number of records in each audit log file.

            This object is now obsolete."
        ::= { ftpAuditLoggingEntry 5 }

    ftpConfigAuditMaximumLogFiles OBJECT-TYPE
        SYNTAX Unsigned32
        MAX-ACCESS read-only
        STATUS obsolete
        DESCRIPTION
            "The maximum number of audit log files.

            This object is now obsolete."
        ::= { ftpAuditLoggingEntry 6 }

--------------------------------------------------------------------------------
--
-- File Protocol Titan / FTP mount points
--
--------------------------------------------------------------------------------

    ftpMountpointNumber OBJECT-TYPE
        SYNTAX Integer32
        MAX-ACCESS read-only
        STATUS obsolete
        DESCRIPTION
            "The number of FTP mount points which are configured
             for the system.

            This object is now obsolete."
        ::= { ftpMountpoints 1 }

    ftpMountpointTable OBJECT-TYPE
        SYNTAX SEQUENCE OF FtpMountpointEntry
        MAX-ACCESS not-accessible
        STATUS obsolete
        DESCRIPTION
            "A table containing the FTP mount point configuration for the
             system.

             The number of entries in this table is given by the value of
             ftpMountpointNumber.

            This object is now obsolete."
        ::= { ftpMountpoints 2 }

    ftpMountpointEntry OBJECT-TYPE
        SYNTAX FtpMountpointEntry
        MAX-ACCESS not-accessible
        STATUS obsolete
        DESCRIPTION
            "FTP mount point information.

            This object is now obsolete."
        INDEX { ftpMountpointName, ftpMountpointEVS }
        ::= { ftpMountpointTable 1 }

    FtpMountpointEntry ::=
        SEQUENCE {
            ftpMountpointName
                DisplayString,
            ftpMountpointEVS
                Integer32,
            ftpMountpointDeviceId
                Integer32,
            ftpMountpointNumberUsers
                Unsigned32
        }

    ftpMountpointName OBJECT-TYPE
        SYNTAX DisplayString
        MAX-ACCESS read-only
        STATUS obsolete
        DESCRIPTION
            "The name of the FTP mount point.  Each FTP mount point
             has a unique name.

            This object is now obsolete."
        ::= { ftpMountpointEntry 1 }

    ftpMountpointEVS OBJECT-TYPE
        SYNTAX Integer32 (0..255)
        MAX-ACCESS read-only
        STATUS obsolete
        DESCRIPTION
            "The ID of the EVS the FTP mount point
             is associated with.

            This object is now obsolete."
        ::= { ftpMountpointEntry 2 }

    ftpMountpointDeviceId OBJECT-TYPE
        SYNTAX Integer32 (1..2147483647)
        MAX-ACCESS read-only
        STATUS obsolete
        DESCRIPTION
            "The device ID of the volume the FTP mount point
             is associated with.

            This object is now obsolete."
        ::= { ftpMountpointEntry 3 }

    ftpMountpointNumberUsers OBJECT-TYPE
        SYNTAX Unsigned32
        MAX-ACCESS read-only
        STATUS obsolete
        DESCRIPTION
            "The number of users of the FTP mount point.

            This object is now obsolete."
        ::= { ftpMountpointEntry 4 }

--------------------------------------------------------------------------------
--
-- File Protocol / FTP / FTP Users
--
--------------------------------------------------------------------------------

    ftpNumberUsers OBJECT-TYPE
        SYNTAX Integer32
        MAX-ACCESS read-only
        STATUS obsolete
        DESCRIPTION
            "The number of FTP users which are configured for the system.

            This object is now obsolete."
        ::= { ftpUser 1 }

    ftpUsersTable OBJECT-TYPE
        SYNTAX SEQUENCE OF FtpUsersEntry
        MAX-ACCESS not-accessible
        STATUS obsolete
        DESCRIPTION
            "A table containing the FTP user configuration for the
             system.

             The number of entries in this table is given by the value of
             ftpNumberUsers.

            This object is now obsolete."
        ::= { ftpUser 2 }

    ftpUsersEntry OBJECT-TYPE
        SYNTAX FtpUsersEntry
        MAX-ACCESS not-accessible
        STATUS obsolete
        DESCRIPTION
            "FTP user information.

            This object is now obsolete."
        INDEX { ftpUsersName, ftpUsersEVS }
        ::= { ftpUsersTable 1 }

    FtpUsersEntry ::=
        SEQUENCE {
            ftpUsersName
                DisplayString,
            ftpUsersEVS
                Integer32,
            ftpUsersMountPointExists
                INTEGER,
            ftpUsersMountPoint
                DisplayString,
            ftpUsersMountInitDirectory
                DisplayString
        }

    ftpUsersName OBJECT-TYPE
        SYNTAX DisplayString
        MAX-ACCESS read-only
        STATUS obsolete
        DESCRIPTION
            "The name of the FTP user.

            This object is now obsolete."
        ::= { ftpUsersEntry 1 }

    ftpUsersEVS OBJECT-TYPE
        SYNTAX Integer32 (0..255)
        MAX-ACCESS read-only
        STATUS obsolete
        DESCRIPTION
            "The ID of the EVS the user
             is associated with.

            This object is now obsolete."
        ::= { ftpUsersEntry 2 }

    ftpUsersMountPointExists OBJECT-TYPE
        SYNTAX INTEGER {
            exists(1),
            doesnotExist(2)
        }
        MAX-ACCESS read-only
        STATUS obsolete
        DESCRIPTION
            "Indicates whether the FTP mount point is configured in
             the ftpMountTable.

            This object is now obsolete."
        ::= { ftpUsersEntry 3 }

    ftpUsersMountPoint OBJECT-TYPE
        SYNTAX DisplayString
        MAX-ACCESS read-only
        STATUS obsolete
        DESCRIPTION
            "The name of the FTP users mount point.

            This object is now obsolete."
        ::= { ftpUsersEntry 4 }

    ftpUsersMountInitDirectory OBJECT-TYPE
        SYNTAX DisplayString
        MAX-ACCESS read-only
        STATUS obsolete
        DESCRIPTION
            "The FTP users initial directory.

            This object is now obsolete."
        ::= { ftpUsersEntry 5 }

--------------------------------------------------------------------------------
--
-- File Protocol / FTP / FTP Statistics
--
--------------------------------------------------------------------------------

    ftpStatisticsTable OBJECT-TYPE
        SYNTAX SEQUENCE OF FtpStatisticsEntry
        MAX-ACCESS not-accessible
        STATUS current
        DESCRIPTION
            "The statistics for the FTP services.

            The number of entries in this table is given by the
            value of clusterPNodeNumber in BLUEARC-SERVER-MIB."
        ::= { ftpStatistics 1 }

    ftpStatisticsEntry OBJECT-TYPE
        SYNTAX FtpStatisticsEntry
        MAX-ACCESS not-accessible
        STATUS current
        DESCRIPTION
            "The statistics for the FTP services."
        INDEX { ftpStatisticsClusterNode }
        ::= { ftpStatisticsTable 1 }

    FtpStatisticsEntry ::=
        SEQUENCE {
            ftpStatisticsClusterNode
                Integer32,
            ftpStatisticsTotalSess
                Counter32,
            ftpStatisticsTotalFtpXferIn
                Counter32,
            ftpStatisticsBytesTotalXferIn
                Counter64,
            ftpStatisticsTotalFtpXferOut
                Counter32,
            ftpStatisticsBytesTotalXferOut
                Counter64,
            ftpStatisticsTotalFtpCommands
                Counter32,
            ftpStatisticsTotalFtpReplies
                Counter32,
            ftpStatisticsTotalBytesCommands
                Counter64,
            ftpStatisticsTotalBytesReplies
                Counter64
        }

    ftpStatisticsClusterNode OBJECT-TYPE
        SYNTAX Integer32 (1..255)
        MAX-ACCESS read-only
        STATUS current
        DESCRIPTION
            "The Cluster Node on which this FTP service
            exists."
        ::= { ftpStatisticsEntry 1 }


    ftpStatisticsTotalSess OBJECT-TYPE
        SYNTAX Counter32
        MAX-ACCESS read-only
        STATUS current
        DESCRIPTION
            "The total number of FTP sessions since power up."
        ::= { ftpStatisticsEntry 2 }

    ftpStatisticsTotalFtpXferIn OBJECT-TYPE
        SYNTAX Counter32
        MAX-ACCESS read-only
        STATUS current
        DESCRIPTION
            "The total number of data transfers (files) in since power up."
        ::= { ftpStatisticsEntry 3 }

    ftpStatisticsBytesTotalXferIn OBJECT-TYPE
        SYNTAX Counter64
        MAX-ACCESS read-only
        STATUS current
        DESCRIPTION
            "The total number of data bytes transferred in since power up."
        ::= { ftpStatisticsEntry 4 }

    ftpStatisticsTotalFtpXferOut OBJECT-TYPE
        SYNTAX Counter32
        MAX-ACCESS read-only
        STATUS current
        DESCRIPTION
            "The total number of data transfers (files) out since power up."
        ::= { ftpStatisticsEntry 5 }

    ftpStatisticsBytesTotalXferOut OBJECT-TYPE
        SYNTAX Counter64
        MAX-ACCESS read-only
        STATUS current
        DESCRIPTION
            "The total number of data bytes transferred out since power up."
        ::= { ftpStatisticsEntry 6 }

    ftpStatisticsTotalFtpCommands OBJECT-TYPE
        SYNTAX Counter32
        MAX-ACCESS read-only
        STATUS current
        DESCRIPTION
            "The total number of commands issued from clients since power up."
        ::= { ftpStatisticsEntry 7 }

    ftpStatisticsTotalFtpReplies OBJECT-TYPE
        SYNTAX Counter32
        MAX-ACCESS read-only
        STATUS current
        DESCRIPTION
            "The total number of replies sent to clients since power up."
        ::= { ftpStatisticsEntry 8 }

    ftpStatisticsTotalBytesCommands OBJECT-TYPE
        SYNTAX Counter64
        MAX-ACCESS read-only
        STATUS current
        DESCRIPTION
            "The total number of bytes received in commands since power up."
        ::= { ftpStatisticsEntry 9 }

    ftpStatisticsTotalBytesReplies OBJECT-TYPE
        SYNTAX Counter64
        MAX-ACCESS read-only
        STATUS current
        DESCRIPTION
            "The total number of bytes set in replies since power up."
        ::= { ftpStatisticsEntry 10 }


--------------------------------------------------------------------------------
--
-- Trap Notifications
--
-- The agent may generate the following traps :
--
-- LinkUp, ColdStart
-- Authentication Failure (if configured)
--
--------------------------------------------------------------------------------

END
