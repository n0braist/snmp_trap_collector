--
-- Copyright 2008 Sun Microsystems, Inc.  All rights reserved.
-- Use is subject to license terms.
--

SUN-HW-TRAP-MIB DEFINITIONS ::= BEGIN

IMPORTS
    OBJECT-TYPE, NOTIFICATION-TYPE, MODULE-IDENTITY, enterprises, Integer32
        FROM SNMPv2-SMI
    TEXTUAL-CONVENTION, DisplayString, RowPointer
        FROM SNMPv2-TC
    OBJECT-GROUP, NOTIFICATION-GROUP
        FROM SNMPv2-CONF;

    sun                 OBJECT IDENTIFIER ::= { enterprises 42 }
    products            OBJECT IDENTIFIER ::= { sun 2 }
    ilom                OBJECT IDENTIFIER ::= { products 175 }

sunHwTrapMIB MODULE-IDENTITY
    LAST-UPDATED    "200904170000Z" -- April 17, 2009
    ORGANIZATION    "Sun Microsystems, Inc."
    CONTACT-INFO    "Sun Microsystems, Inc.
                     4150 Network Circle
                     Santa Clara, CA 95054

                     1-800-555-9SUN or
                     1-650-960-1300

                     http://www.sun.com
                     or contact your local support representative"
    DESCRIPTION
        "Copyright 2008 Sun Microsystems, Inc.  All rights reserved.
         Use is subject to license terms.

         The SUN-HW-TRAP-MIB describes the hardware related
         notifications/traps that may be generated by Sun systems"

    REVISION        
        "200904170000Z" -- April 17, 2009
    DESCRIPTION     
        "Version: 2.1
         Released with ILOM version 3.0"
    REVISION
        "200810290000Z" -- October 29, 2008
    DESCRIPTION
        "Version: 1.1
         Added keywords for HP SIM integration"
    REVISION    
        "200702060000Z" -- February 6, 2007
    DESCRIPTION 
        "Version: 1.0"

    ::= { ilom 103 }

sunHwTrapObjects           OBJECT IDENTIFIER ::= { sunHwTrapMIB 1 }
sunHwTraps                 OBJECT IDENTIFIER ::= { sunHwTrapMIB 2 }
sunHwTrapPrefix            OBJECT IDENTIFIER ::= { sunHwTraps 0 }
sunHwTrapData              OBJECT IDENTIFIER ::= { sunHwTraps 1 }
sunHwTrapConformances      OBJECT IDENTIFIER ::= { sunHwTrapMIB 3 }
sunHwTrapCompliances       OBJECT IDENTIFIER ::= { sunHwTrapConformances 1 }
sunHwTrapGroups            OBJECT IDENTIFIER ::= { sunHwTrapConformances 2 }
sunHwTrapObjectGroups      OBJECT IDENTIFIER ::= { sunHwTrapGroups 1 }
sunHwTrapNotifGroups       OBJECT IDENTIFIER ::= { sunHwTrapGroups 2 }


--
-- Textual Conventions
--

SunHwTrapThresholdTypeTC ::= TEXTUAL-CONVENTION
    STATUS current
    DESCRIPTION
        "Describes whether a threshold is an upper threshold or
         a lower threshold"
    SYNTAX INTEGER {
        upper(1),
        lower(2),
        unknown(3)
    }

SunHwTrapSeverityTC ::= TEXTUAL-CONVENTION
    STATUS current
    DESCRIPTION
        "Describes the severity levels that a trap can take."
    SYNTAX INTEGER {
        other(1),
        fatal(2),
        critical(3),
        nonCritical(4),
        ok(5)
    }

SunHwTrapHAStateTC ::= TEXTUAL-CONVENTION
    STATUS current
    DESCRIPTION
        "Describes the states that a high availability system can take."
    SYNTAX INTEGER {
        other(1),
        initializing(2),
        standalone(3),
        standby(4),
        master(5)
    }

SunHwTrapHardDriveStatesTC ::= TEXTUAL-CONVENTION
    STATUS current
    DESCRIPTION
        "Describes the states a hard drive can be in when hard drive status
         is reported."
    SYNTAX INTEGER {
        other(1),
        present(2),
        fault(3),
        predictiveFailure(4),
        hotSpare(5),
        consistencyCheckInProgress(6),
        inCriticalArray(7),
        inFailedArray(8),
        rebuildInProgress(9),
        rebuildAborted(10)
    }

SunHwTrapDisableReasonsTC ::= TEXTUAL-CONVENTION
    STATUS current
    DESCRIPTION
        "Describes the reasons that a component is disabled."
    SYNTAX INTEGER {
        unknown(1),
        faultOrError(2),
        configuration(3)
    }

SunHwTrapFloatingPointValueTC ::= TEXTUAL-CONVENTION
    DISPLAY-HINT "255a"
    STATUS       current
    DESCRIPTION
        "A floating point number converted to a string
         in decimal notation of the form [-]mmm.dd"
    SYNTAX OCTET STRING (SIZE (0..255))

--
-- MIB Notification specific data
--

sunHwTrapSystemIdentifier OBJECT-TYPE
    SYNTAX DisplayString
    MAX-ACCESS accessible-for-notify
    STATUS current
    DESCRIPTION
        "A text string used to identify the source of the trap. Typically
         this is the host name."
    ::= { sunHwTrapData 1 }

sunHwTrapComponentName OBJECT-TYPE
    SYNTAX DisplayString
    MAX-ACCESS accessible-for-notify
    STATUS current
    DESCRIPTION
        "The name of the component which is the source of the trap."
    ::= { sunHwTrapData 2 }

sunHwTrapThresholdType OBJECT-TYPE
    SYNTAX SunHwTrapThresholdTypeTC
    MAX-ACCESS accessible-for-notify
    STATUS current
    DESCRIPTION
        "Identifies the threshold type that the sensor is reporting on."
    ::= { sunHwTrapData 3 }

sunHwTrapThresholdValue OBJECT-TYPE
    SYNTAX SunHwTrapFloatingPointValueTC
    MAX-ACCESS accessible-for-notify
    STATUS current
    DESCRIPTION
        "The threshold setting that has been crossed."
    ::= { sunHwTrapData 4 }

sunHwTrapSensorValue OBJECT-TYPE
    SYNTAX SunHwTrapFloatingPointValueTC
    MAX-ACCESS accessible-for-notify
    STATUS current
    DESCRIPTION
        "The threshold sensor's reading at the time the trap was generated."
    ::= { sunHwTrapData 5 }

sunHwTrapSuspectComponentName OBJECT-TYPE
    SYNTAX DisplayString
    MAX-ACCESS accessible-for-notify
    STATUS current
    DESCRIPTION
        "Contains the name of a component that is suspected of causing
         a fault."
    ::= { sunHwTrapData 6 }

sunHwTrapFaultClass OBJECT-TYPE
    SYNTAX DisplayString
    MAX-ACCESS accessible-for-notify
    STATUS current
    DESCRIPTION
        "The class represents a hierarchical classification string indicating
         the type of problem detected, as reported by the fault management
         subsystem, such as, for instance the Solaris fault manager.
         Information on the Solaris fault manager can be found at
         http://www.opensolaris.org/os/community/fm.

         This object will have a value of NULL if the system doesn't
         support this information."
    REFERENCE
        "SUN-FM-MIB.sunFmFaultEventClass
         http://www.opensolaris.org/os/community/fm/mib/sun-fm-mib.mib"

    ::= { sunHwTrapData 7 }

sunHwTrapFaultCertainty OBJECT-TYPE
    SYNTAX Integer32 (0..100)
    MAX-ACCESS accessible-for-notify
    STATUS current
    DESCRIPTION
        "The percentage likelihood that the component is the source
         of the problem. This object will have a value of 0 if the
         system doesn't support this information."
    ::= { sunHwTrapData 8 }

sunHwTrapAdditionalInfo OBJECT-TYPE
    SYNTAX DisplayString
    MAX-ACCESS accessible-for-notify
    STATUS current
    DESCRIPTION
        "An optional textual description which provides additional
         information relevant to this notification."
    ::= { sunHwTrapData 9 }

sunHwTrapAssocObjectId OBJECT-TYPE
    SYNTAX RowPointer
    MAX-ACCESS accessible-for-notify
    STATUS current
    DESCRIPTION
        "The object in the entPhysicalTable to which this notification applies.
         The value is the name of the instance of the first accessible columnar
         object in the entPhysicalTable conceptual row. If no association exists
         or the association cannot be determined, this object will have a value
         of 0.0."
    ::= { sunHwTrapData 10 }

sunHwTrapNewHAState OBJECT-TYPE
    SYNTAX SunHwTrapHAStateTC
    MAX-ACCESS accessible-for-notify
    STATUS current
    DESCRIPTION
        "This object provides the new value of the high availability state
         after a high availability state change has occurred."
    ::= { sunHwTrapData 11 }

sunHwTrapOldHAState OBJECT-TYPE
    SYNTAX SunHwTrapHAStateTC
    MAX-ACCESS accessible-for-notify
    STATUS current
    DESCRIPTION
        "This object provides the old value of the high availability state
         after a high availability state change has occurred."
    ::= { sunHwTrapData 12 }

sunHwTrapSeverity OBJECT-TYPE
    SYNTAX SunHwTrapSeverityTC
    MAX-ACCESS accessible-for-notify
    STATUS current
    DESCRIPTION
        "An indication of the severity of the notfication."
    ::= { sunHwTrapData 13 }

sunHwTrapChassisId OBJECT-TYPE
    SYNTAX DisplayString
    MAX-ACCESS accessible-for-notify
    STATUS current
    DESCRIPTION
        "A text string containing the chassis serial number. When combined
         with the sunHwTrapProductName, it unambiguously identifies the
         system. If the source of the trap is a blade, the text string will
         contain the chassis serial number and the blade serial number, in
         the following format <chassis-serial-number::blade-serial-number>"
    ::= { sunHwTrapData 14 }

sunHwTrapProductName OBJECT-TYPE
    SYNTAX DisplayString
    MAX-ACCESS accessible-for-notify
    STATUS current
    DESCRIPTION
        "A text string containing the product name. When combined with the
         sunHwTrapChassisId, it unambiguously identifies the system. If the
         source of the trap is a blade, the text string will contain the
         chassis product name and the blade product name, in the following
         format <chassis-name>::<blade-name>"
    ::= { sunHwTrapData 15 }

sunHwTrapHardDriveState OBJECT-TYPE
    SYNTAX SunHwTrapHardDriveStatesTC
    MAX-ACCESS accessible-for-notify
    STATUS current
    DESCRIPTION
        "The states a hard drive can be in when hard drive status
         is reported."
    ::= { sunHwTrapData 16 }

sunHwTrapFaultMessageID OBJECT-TYPE
    SYNTAX DisplayString
    MAX-ACCESS accessible-for-notify
    STATUS current
    DESCRIPTION
        "The message ID that can be used to get additional information about
         the problem from Sun's knowledge article database. This object will
         have a value of NULL if the system doesn't support this
         information."
    ::= { sunHwTrapData 17 }

sunHwTrapFaultUUID OBJECT-TYPE
    SYNTAX DisplayString
    MAX-ACCESS accessible-for-notify
    STATUS current
    DESCRIPTION
        "The universal unique identifier that was assigned to this fault. This
         object will have a value of NULL if the system doesn't support this
         information."
    ::= { sunHwTrapData 18 }

sunHwTrapDisableReason OBJECT-TYPE
    SYNTAX SunHwTrapDisableReasonsTC
    MAX-ACCESS accessible-for-notify
    STATUS current
    DESCRIPTION
        "An indication as to why the component was disabled."
    ::= { sunHwTrapData 19 } 

sunHwTrapTestMessage OBJECT-TYPE
    SYNTAX DisplayString
    MAX-ACCESS accessible-for-notify
    STATUS current
    DESCRIPTION
        "This is a test trap"
    ::= { sunHwTrapData 20 }
--
-- MIB Notifications
--

sunHwTrapVoltageFatalThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A voltage sensor has reported that its value has gone above an upper
         fatal threshold setting or below a lower fatal threshold setting.
         The sunHwTrapThresholdType object indicates whether the threshold was
         an upper or lower."
--  Keywords for HP SIM integration
--#TYPE       "A voltage sensor has reported that its value has gone above an upper fatal threshold setting or below a lower fatal threshold setting. The sunHwTrapThresholdType object indicates whether the threshold was an upper or lower."
--#SUMMARY    "A voltage sensor has reported that its value has gone above an upper fatal threshold setting or below a lower fatal threshold setting. The sunHwTrapThresholdType object indicates whether the threshold was an upper or lower."
--#ARGUMENTS  {}
--#SEVERITY   CRITICAL
    ::= { sunHwTrapPrefix 1 }

sunHwTrapVoltageFatalThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A voltage sensor has reported that its value has gone below an upper
         fatal threshold setting or above a lower fatal threshold setting.
         The sunHwTrapThresholdType object indicates whether the threshold was
         an upper or lower."
--  Keywords for HP SIM integration
--#TYPE       "A voltage sensor has reported that its value has gone below an upper fatal threshold setting or above a lower fatal threshold setting. The sunHwTrapThresholdType object indicates whether the threshold was an upper or lower."
--#SUMMARY    "A voltage sensor has reported that its value has gone below an upper fatal threshold setting or above a lower fatal threshold setting.  The sunHwTrapThresholdType object indicates whether the threshold was an upper or lower."
--#ARGUMENTS  {}
--#SEVERITY   INFORMATIONAL
    ::= { sunHwTrapPrefix 2 }

sunHwTrapVoltageCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
     }
    STATUS    current
    DESCRIPTION
        "A voltage sensor has reported that its value has gone above an upper
         critical threshold setting or below a lower critical threshold setting.
         The sunHwTrapThresholdType object indicates whether the threshold was
         an upper or lower."
--  Keywords for HP SIM integration
--#TYPE       "A voltage sensor has reported that its value has gone above an upper critical threshold setting or below a lower critical threshold setting. The sunHwTrapThresholdType object indicates whether the threshold was an upper or lower."
--#SUMMARY    "A voltage sensor has reported that its value has gone above an upper critical threshold setting or below a lower critical threshold setting. The sunHwTrapThresholdType object indicates whether the threshold was an upper or lower."
--#ARGUMENTS  {}
--#SEVERITY   MAJOR
    ::= { sunHwTrapPrefix 3 }

sunHwTrapVoltageCritThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
     }
    STATUS    current
    DESCRIPTION
        "A voltage sensor has reported that its value has gone below an upper
         critical threshold setting or above a lower critical threshold setting.
         The sunHwTrapThresholdType object indicates whether the threshold was
         an upper or lower."
--  Keywords for HP SIM integration
--#TYPE       "A voltage sensor has reported that its value has gone below an upper critical threshold setting or above a lower critical threshold setting. The sunHwTrapThresholdType object indicates whether the threshold was an upper or lower."
--#SUMMARY    "A voltage sensor has reported that its value has gone below an upper critical threshold setting or above a lower critical threshold setting. The sunHwTrapThresholdType object indicates whether the threshold was an upper or lower."
--#ARGUMENTS  {}
--#SEVERITY   INFORMATIONAL
    ::= { sunHwTrapPrefix 4 }

sunHwTrapVoltageNonCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A voltage sensor has reported that its value has gone above an upper
         non-critical threshold setting or below a lower non-critical threshold
         setting. The sunHwTrapThresholdType object indicates whether the threshold
         was an upper or lower."
--  Keywords for HP SIM integration
--#TYPE       "A voltage sensor has reported that its value has gone above an upper non-critical threshold setting or below a lower non-critical threshold setting. The sunHwTrapThresholdType object indicates whether the threshold was an upper or lower."
--#SUMMARY    "A voltage sensor has reported that its value has gone above an upper non-critical threshold setting or below a lower non-critical threshold setting. The sunHwTrapThresholdType object indicates whether the threshold was an upper or lower."
--#ARGUMENTS  {}
--#SEVERITY   MINOR
    ::= { sunHwTrapPrefix 5 }

sunHwTrapVoltageOk NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A voltage sensor has reported that its value is in the normal
         operating range."
--  Keywords for HP SIM integration
--#TYPE       "A voltage sensor has reported that its value is in the normal operating range."
--#SUMMARY    "A voltage sensor has reported that its value is in the normal operating range."
--#ARGUMENTS  {}
--#SEVERITY   INFORMATIONAL
    ::= { sunHwTrapPrefix 6 }

sunHwTrapTempFatalThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A temperature sensor has reported that its value has gone above an upper
         fatal threshold setting or below a lower fatal threshold setting.
         The sunHwTrapThresholdType object indicates whether the threshold was
         an upper or lower."
--  Keywords for HP SIM integration
--#TYPE       "A temperature sensor has reported that its value has gone above an upper fatal threshold setting or below a lower fatal threshold setting. The sunHwTrapThresholdType object indicates whether the threshold was an upper or lower."
--#SUMMARY    "A temperature sensor has reported that its value has gone above an upper fatal threshold setting or below a lower fatal threshold setting. The sunHwTrapThresholdType object indicates whether the threshold was an upper or lower."
--#ARGUMENTS  {}
--#SEVERITY   CRITICAL
    ::= { sunHwTrapPrefix 7 }

sunHwTrapTempFatalThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A temperature sensor has reported that its value has gone below an
         upper fatal threshold setting or above a lower fatal threshold setting.
         The sunHwTrapThresholdType object indicates whether the threshold was
         an upper or lower."
--  Keywords for HP SIM integration
--#TYPE       "A temperature sensor has reported that its value has gone below an upper fatal threshold setting or above a lower fatal threshold setting. The sunHwTrapThresholdType object indicates whether the threshold was an upper or lower."
--#SUMMARY    "A temperature sensor has reported that its value has gone below an upper fatal threshold setting or above a lower fatal threshold setting. The sunHwTrapThresholdType object indicates whether the threshold was an upper or lower."
--#ARGUMENTS  {}
--#SEVERITY   INFORMATIONAL
    ::= { sunHwTrapPrefix 8 }

sunHwTrapTempCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A temperature sensor has reported that its value has gone above an
         upper critical threshold setting or below a lower critical threshold
         setting. The sunHwTrapThresholdType object indicates whether the
         threshold was an upper or lower."
--  Keywords for HP SIM integration
--#TYPE       "A temperature sensor has reported that its value has gone above an upper critical threshold setting or below a lower critical threshold setting. The sunHwTrapThresholdType object indicates whether the threshold was an upper or lower."
--#SUMMARY    "A temperature sensor has reported that its value has gone above an upper critical threshold setting or below a lower critical threshold setting. The sunHwTrapThresholdType object indicates whether the threshold was an upper or lower."
--#ARGUMENTS  {}
--#SEVERITY   MAJOR
    ::= { sunHwTrapPrefix 9 }

sunHwTrapTempCritThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A temperature sensor has reported that its value has gone below an
         upper critical threshold setting or above a lower critical threshold
         setting. The sunHwTrapThresholdType object indicates whether the
         threshold was an upper or lower."
--  Keywords for HP SIM integration
--#TYPE       "A temperature sensor has reported that its value has gone below an upper critical threshold setting or above a lower critical threshold setting. The sunHwTrapThresholdType object indicates whether the threshold was an upper or lower."
--#SUMMARY    "A temperature sensor has reported that its value has gone below an upper critical threshold setting or above a lower critical threshold setting. The sunHwTrapThresholdType object indicates whether the threshold was an upper or lower."
--#ARGUMENTS  {}
--#SEVERITY   INFORMATIONAL
    ::= { sunHwTrapPrefix 10 }

sunHwTrapTempNonCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A temperature sensor has reported that its value has gone above an
         upper non-critical threshold setting or below a lower non-critical
         threshold setting. The sunHwTrapThresholdType object indicates whether
         the threshold was an upper or lower."
--  Keywords for HP SIM integration
--#TYPE       "A temperature sensor has reported that its value has gone above an upper non-critical threshold setting or below a lower non-critical threshold setting. The sunHwTrapThresholdType object indicates whether the threshold was an upper or lower."
--#SUMMARY    "A temperature sensor has reported that its value has gone above an upper non-critical threshold setting or below a lower non-critical threshold setting. The sunHwTrapThresholdType object indicates whether the threshold was an upper or lower."
--#ARGUMENTS  {}
--#SEVERITY   MINOR
    ::= { sunHwTrapPrefix 11 }

sunHwTrapTempOk NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A temperature sensor has reported that its value is in the normal
         operating range."
--  Keywords for HP SIM integration
--#TYPE       "A temperature sensor has reported that its value is in the normal operating range."
--#SUMMARY    "A temperature sensor has reported that its value is in the normal operating range."
--#ARGUMENTS  {}
--#SEVERITY   INFORMATIONAL
    ::= { sunHwTrapPrefix 12 }

sunHwTrapElectricalCurrentFatalThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "An electrical current sensor has reported that its value has gone above
         an upper fatal threshold setting or below a lower fatal threshold
         setting. The sunHwTrapThresholdType object indicates whether the
         threshold was an upper or lower."
--  Keywords for HP SIM integration
--#TYPE       "An electrical current sensor has reported that its value has gone above an upper fatal threshold setting or below a lower fatal threshold setting. The sunHwTrapThresholdType object indicates whether the threshold was an upper or lower."
--#SUMMARY    "An electrical current sensor has reported that its value has gone above an upper fatal threshold setting or below a lower fatal threshold setting. The sunHwTrapThresholdType object indicates whether the threshold was an upper or lower."
--#ARGUMENTS  {}
--#SEVERITY   CRITICAL
    ::= { sunHwTrapPrefix 13 }

sunHwTrapElectricalCurrentFatalThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "An electrical current sensor has reported that its value has gone below
         an upper fatal threshold setting or above a lower fatal threshold
         setting. The sunHwTrapThresholdType object indicates whether the
         threshold was an upper or lower."
--  Keywords for HP SIM integration
--#TYPE       "An electrical current sensor has reported that its value has gone below an upper fatal threshold setting or above a lower fatal threshold setting. The sunHwTrapThresholdType object indicates whether the threshold was an upper or lower."
--#SUMMARY    "An electrical current sensor has reported that its value has gone below an upper fatal threshold setting or above a lower fatal threshold setting. The sunHwTrapThresholdType object indicates whether the threshold was an upper or lower."
--#ARGUMENTS  {}
--#SEVERITY   INFORMATIONAL
    ::= { sunHwTrapPrefix 14 }

sunHwTrapElectricalCurrentCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "An electrical current sensor has reported that its value has gone above
         an upper critical threshold setting or below a lower critical threshold
         setting. The sunHwTrapThresholdType object indicates whether the
         threshold was an upper or lower."
--  Keywords for HP SIM integration
--#TYPE       "An electrical current sensor has reported that its value has gone above an upper critical threshold setting or below a lower critical threshold setting. The sunHwTrapThresholdType object indicates whether the threshold was an upper or lower."
--#SUMMARY    "An electrical current sensor has reported that its value has gone above an upper critical threshold setting or below a lower critical threshold setting. The sunHwTrapThresholdType object indicates whether the threshold was an upper or lower."
--#ARGUMENTS  {}
--#SEVERITY   MAJOR
    ::= { sunHwTrapPrefix 15 }

sunHwTrapElectricalCurrentCritThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "An electrical current sensor has reported that its value has gone below
         an upper critical threshold setting or above a lower critical threshold
         setting. The sunHwTrapThresholdType object indicates whether the
         threshold was an upper or lower."
--  Keywords for HP SIM integration
--#TYPE       "An electrical current sensor has reported that its value has gone below an upper critical threshold setting or above a lower critical threshold setting. The sunHwTrapThresholdType object indicates whether the threshold was an upper or lower."
--#SUMMARY    "An electrical current sensor has reported that its value has gone below an upper critical threshold setting or above a lower critical threshold setting. The sunHwTrapThresholdType object indicates whether the threshold was an upper or lower."
--#ARGUMENTS  {}
--#SEVERITY   INFORMATIONAL
    ::= { sunHwTrapPrefix 16 }

sunHwTrapElectricalCurrentNonCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "An electrical current sensor has reported that its value has gone above
         an upper non-critical threshold setting or below a lower non-critical
         threshold setting. The sunHwTrapThresholdType object indicates whether
         the threshold was an upper or lower."
--  Keywords for HP SIM integration
--#TYPE       "An electrical current sensor has reported that its value has gone above an upper non-critical threshold setting or below a lower non-critical threshold setting. The sunHwTrapThresholdType object indicates whether the threshold was an upper or lower."
--#SUMMARY    "An electrical current sensor has reported that its value has gone above an upper non-critical threshold setting or below a lower non-critical threshold setting. The sunHwTrapThresholdType object indicates whether the threshold was an upper or lower."
--#ARGUMENTS  {}
--#SEVERITY   MINOR
    ::= { sunHwTrapPrefix 17 }

sunHwTrapElectricalCurrentOk NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "An electrical current sensor has reported that its value is in
         the normal operating range."
--  Keywords for HP SIM integration
--#TYPE       "An electrical current sensor has reported that its value is in the normal operating range."
--#SUMMARY    "An electrical current sensor has reported that its value is in the normal operating range."
--#ARGUMENTS  {}
--#SEVERITY   INFORMATIONAL
    ::= { sunHwTrapPrefix 18 }

sunHwTrapFanSpeedFatalThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A fan speed sensor has reported that its value has gone above an upper
         fatal threshold setting or below a lower fatal threshold setting.
         The sunHwTrapThresholdType object indicates whether the threshold was
         an upper or lower."
--  Keywords for HP SIM integration
--#TYPE       "A fan speed sensor has reported that its value has gone above an upper fatal threshold setting or below a lower fatal threshold setting. The sunHwTrapThresholdType object indicates whether the threshold was an upper or lower."
--#SUMMARY    "A fan speed sensor has reported that its value has gone above an upper fatal threshold setting or below a lower fatal threshold setting. The sunHwTrapThresholdType object indicates whether the threshold was an upper or lower."
--#ARGUMENTS  {}
--#SEVERITY   CRITICAL
    ::= { sunHwTrapPrefix 19 }

sunHwTrapFanSpeedFatalThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A fan speed sensor has reported that its value has gone below an upper
         fatal threshold setting or above a lower fatal threshold setting.
         The sunHwTrapThresholdType object indicates whether the threshold was
         an upper or lower."
--  Keywords for HP SIM integration
--#TYPE       "A fan speed sensor has reported that its value has gone below an upper fatal threshold setting or above a lower fatal threshold setting. The sunHwTrapThresholdType object indicates whether the threshold was an upper or lower."
--#SUMMARY    "A fan speed sensor has reported that its value has gone below an upper fatal threshold setting or above a lower fatal threshold setting. The sunHwTrapThresholdType object indicates whether the threshold was an upper or lower."
--#ARGUMENTS  {}
--#SEVERITY   INFORMATIONAL
    ::= { sunHwTrapPrefix 20 }

sunHwTrapFanSpeedCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A fan speed sensor has reported that its value has gone above an upper
         critical threshold setting or below a lower critical threshold setting.
         The sunHwTrapThresholdType object indicates whether the threshold was
         an upper or lower."
--  Keywords for HP SIM integration
--#TYPE       "A fan speed sensor has reported that its value has gone above an upper critical threshold setting or below a lower critical threshold setting. The sunHwTrapThresholdType object indicates whether the threshold was an upper or lower."
--#SUMMARY    "A fan speed sensor has reported that its value has gone above an upper critical threshold setting or below a lower critical threshold setting. The sunHwTrapThresholdType object indicates whether the threshold was an upper or lower."
--#ARGUMENTS  {}
--#SEVERITY   MAJOR
    ::= { sunHwTrapPrefix 21 }

sunHwTrapFanSpeedCritThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A fan speed sensor has reported that its value has gone below an upper
         critical threshold setting or above a lower critical threshold setting.
         The sunHwTrapThresholdType object indicates whether the threshold was
         an upper or lower."
--  Keywords for HP SIM integration
--#TYPE       "A fan speed sensor has reported that its value has gone below an upper critical threshold setting or above a lower critical threshold setting. The sunHwTrapThresholdType object indicates whether the threshold was an upper or lower."
--#SUMMARY    "A fan speed sensor has reported that its value has gone below an upper critical threshold setting or above a lower critical threshold setting. The sunHwTrapThresholdType object indicates whether the threshold was an upper or lower."
--#ARGUMENTS  {}
--#SEVERITY   INFORMATIONAL
    ::= { sunHwTrapPrefix 22 }

sunHwTrapFanSpeedNonCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A fan speed sensor has reported that its value has gone above an upper
         non-critical threshold setting or below a lower non-critical threshold
         setting. The sunHwTrapThresholdType object indicates whether the
         threshold was an upper or lower."
--  Keywords for HP SIM integration
--#TYPE       "A fan speed sensor has reported that its value has gone above an upper non-critical threshold setting or below a lower non-critical threshold setting. The sunHwTrapThresholdType object indicates whether the threshold was an upper or lower."
--#SUMMARY    "A fan speed sensor has reported that its value has gone above an upper non-critical threshold setting or below a lower non-critical threshold setting. The sunHwTrapThresholdType object indicates whether the threshold was an upper or lower."
--#ARGUMENTS  {}
--#SEVERITY   MINOR
    ::= { sunHwTrapPrefix 23 }

sunHwTrapFanSpeedOk NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A fan speed sensor has reported that its value is in
         the normal operating range."
--  Keywords for HP SIM integration
--#TYPE       "A fan speed sensor has reported that its value is in the normal operating range."
--#SUMMARY    "A fan speed sensor has reported that its value is in the normal operating range."
--#ARGUMENTS  {}
--#SEVERITY   INFORMATIONAL
    ::= { sunHwTrapPrefix 24 }

sunHwTrapSensorFatalThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A sensor has reported that its value has gone above an upper fatal
         threshold setting or below a lower fatal threshold setting. The 
         generic 'sensor' trap is generated when the SNMP agent does not
         recognize the component type. The sunHwTrapThresholdType object
         indicates whether the threshold was an upper or lower."
--  Keywords for HP SIM integration
--#TYPE       "A sensor has reported that its value has gone above an upper fatal threshold setting or below a lower fatal threshold setting. The  generic 'sensor' trap is generated when the SNMP agent does not recognize the component type. The sunHwTrapThresholdType object indicates whether the threshold was an upper or lower."
--#SUMMARY    "A sensor has reported that its value has gone above an upper fatal threshold setting or below a lower fatal threshold setting. The  generic 'sensor' trap is generated when the SNMP agent does not recognize the component type. The sunHwTrapThresholdType object indicates whether the threshold was an upper or lower."
--#ARGUMENTS  {}
--#SEVERITY   CRITICAL
    ::= { sunHwTrapPrefix 25 }

sunHwTrapSensorFatalThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A sensor has reported that its value has gone below an upper fatal
         threshold setting or above a lower fatal threshold setting. The
         generic 'sensor' trap is generated when the SNMP agent does not
         recognize the component type. The sunHwTrapThresholdType object
         indicates whether the threshold was an upper or lower."
--  Keywords for HP SIM integration
--#TYPE       "A sensor has reported that its value has gone below an upper fatal threshold setting or above a lower fatal threshold setting. The generic 'sensor' trap is generated when the SNMP agent does not recognize the component type. The sunHwTrapThresholdType object indicates whether the threshold was an upper or lower."
--#SUMMARY    "A sensor has reported that its value has gone below an upper fatal threshold setting or above a lower fatal threshold setting. The generic 'sensor' trap is generated when the SNMP agent does not recognize the component type. The sunHwTrapThresholdType object indicates whether the threshold was an upper or lower."
--#ARGUMENTS  {}
--#SEVERITY   INFORMATIONAL
    ::= { sunHwTrapPrefix 26 }

sunHwTrapSensorCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A sensor has reported that its value has gone above an upper critical
         threshold setting or below a lower critical threshold setting. The 
         generic 'sensor' trap is generated when the SNMP agent does not
         recognize the component type. The sunHwTrapThresholdType object
         indicates whether the threshold was an upper or lower."
--  Keywords for HP SIM integration
--#TYPE       "A sensor has reported that its value has gone above an upper critical threshold setting or below a lower critical threshold setting. The  generic 'sensor' trap is generated when the SNMP agent does not recognize the component type. The sunHwTrapThresholdType object indicates whether the threshold was an upper or lower."
--#SUMMARY    "A sensor has reported that its value has gone above an upper critical threshold setting or below a lower critical threshold setting. The  generic 'sensor' trap is generated when the SNMP agent does not recognize the component type. The sunHwTrapThresholdType object indicates whether the threshold was an upper or lower."
--#ARGUMENTS  {}
--#SEVERITY   MAJOR
    ::= { sunHwTrapPrefix 27 }

sunHwTrapSensorCritThresholdDeasserted NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A sensor has reported that its value has gone below an upper critical
         threshold setting or above a lower critical threshold setting. The
         generic 'sensor' trap is generated when the SNMP agent does not
         recognize the component type. The sunHwTrapThresholdType object
         indicates whether the threshold was an upper or lower."
--  Keywords for HP SIM integration
--#TYPE       "A sensor has reported that its value has gone below an upper critical threshold setting or above a lower critical threshold setting. The generic 'sensor' trap is generated when the SNMP agent does not recognize the component type. The sunHwTrapThresholdType object indicates whether the threshold was an upper or lower."
--#SUMMARY    "A sensor has reported that its value has gone below an upper critical threshold setting or above a lower critical threshold setting. The generic 'sensor' trap is generated when the SNMP agent does not recognize the component type. The sunHwTrapThresholdType object indicates whether the threshold was an upper or lower."
--#ARGUMENTS  {}
--#SEVERITY   INFORMATIONAL
    ::= { sunHwTrapPrefix 28 }

sunHwTrapSensorNonCritThresholdExceeded NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A sensor has reported that its value has gone above an upper
         non-critical threshold setting or below a lower non-critical threshold
         setting. The generic 'sensor' trap is generated when the SNMP agent
         does not recognize the component type. The sunHwTrapThresholdType
         object indicates whether the threshold was an upper or lower."
--  Keywords for HP SIM integration
--#TYPE       "A sensor has reported that its value has gone above an upper non-critical threshold setting or below a lower non-critical threshold setting. The generic 'sensor' trap is generated when the SNMP agent does not recognize the component type. The sunHwTrapThresholdType object indicates whether the threshold was an upper or lower."
--#SUMMARY    "A sensor has reported that its value has gone above an upper non-critical threshold setting or below a lower non-critical threshold setting. The generic 'sensor' trap is generated when the SNMP agent does not recognize the component type. The sunHwTrapThresholdType object indicates whether the threshold was an upper or lower."
--#ARGUMENTS  {}
--#SEVERITY   MINOR
    ::= { sunHwTrapPrefix 29 }

sunHwTrapSensorThresholdOk NOTIFICATION-TYPE
    OBJECTS { sunHwTrapSystemIdentifier,
              sunHwTrapChassisId,
              sunHwTrapProductName,
              sunHwTrapComponentName,
              sunHwTrapThresholdType,
              sunHwTrapThresholdValue,
              sunHwTrapSensorValue,
              sunHwTrapAdditionalInfo,
              sunHwTrapAssocObjectId,
              sunHwTrapSeverity
    }
    STATUS    current
    DESCRIPTION
        "A sensor has reported that its value is in the normal operating range.
         The generic 'sensor' trap is generated when the SNMP agent does not
         recognize the component type."
--  Keywords for HP SIM integration
--#TYPE       "A sensor has reported that its value is in the normal operating range. The generic 'sensor' trap is generated when the SNMP agent does not recognize the component type."
--#SUMMARY    "A sensor has reported that its value is in the normal operating range. The generic 'sensor' trap is generated when the SNMP agent does not recognize the component type."
--#ARGUMENTS  {}
--#SEVERITY   INFORMATIONAL
    ::= { sunHwTrapPrefix 30 }

sunHwTrapPowerSupplyFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A power supply component is suspected of causing a fault."
--  Keywords for HP SIM integration
--#TYPE       "A power supply component is suspected of causing a fault."
--#SUMMARY    "A power supply component is suspected of causing a fault."
--#ARGUMENTS  {}
--#SEVERITY   MAJOR
    ::= { sunHwTrapPrefix 31 }

sunHwTrapPowerSupplyFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "A power supply component fault has been cleared."
--  Keywords for HP SIM integration
--#TYPE       "A power supply component fault has been cleared."
--#SUMMARY    "A power supply component fault has been cleared."
--#ARGUMENTS  {}
--#SEVERITY   INFORMATIONAL
    ::= { sunHwTrapPrefix 64 }

sunHwTrapPowerSupplyError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A power supply sensor has detected an error."
--  Keywords for HP SIM integration
--#TYPE       "A power supply sensor has detected an error."
--#SUMMARY    "A power supply sensor has detected an error."
--#ARGUMENTS  {}
--#SEVERITY   MAJOR
    ::= { sunHwTrapPrefix 32 }

sunHwTrapPowerSupplyOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A power supply sensor has returned to its normal state."
--  Keywords for HP SIM integration
--#TYPE       "A power supply sensor has returned to its normal state."
--#SUMMARY    "A power supply sensor has returned to its normal state."
--#ARGUMENTS  {}
--#SEVERITY   INFORMATIONAL
    ::= { sunHwTrapPrefix 33 }

sunHwTrapFanFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A fan component is suspected of causing a fault."
--  Keywords for HP SIM integration
--#TYPE       "A fan component is suspected of causing a fault."
--#SUMMARY    "A fan component is suspected of causing a fault."
--#ARGUMENTS  {}
--#SEVERITY   MAJOR
    ::= { sunHwTrapPrefix 34 }

sunHwTrapFanFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "A fan component fault has been cleared."
--  Keywords for HP SIM integration
--#TYPE       "A fan component fault has been cleared."
--#SUMMARY    "A fan component fault has been cleared."
--#ARGUMENTS  {}
--#SEVERITY   INFORMATIONAL
    ::= { sunHwTrapPrefix 65 }

sunHwTrapFanError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A fan sensor has detected an error."
--  Keywords for HP SIM integration
--#TYPE       "A fan sensor has detected an error."
--#SUMMARY    "A fan sensor has detected an error."
--#ARGUMENTS  {}
--#SEVERITY   MAJOR
    ::= { sunHwTrapPrefix 35 }

sunHwTrapFanOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A fan sensor has returned to its normal state."
--  Keywords for HP SIM integration
--#TYPE       "A fan sensor has returned to its normal state."
--#SUMMARY    "A fan sensor has returned to its normal state."
--#ARGUMENTS  {}
--#SEVERITY   INFORMATIONAL
    ::= { sunHwTrapPrefix 36 }

sunHwTrapProcessorFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A processor component is suspected of causing a fault."
--  Keywords for HP SIM integration
--#TYPE       "A processor component is suspected of causing a fault."
--#SUMMARY    "A processor component is suspected of causing a fault."
--#ARGUMENTS  {}
--#SEVERITY   MAJOR
    ::= { sunHwTrapPrefix 37 }

sunHwTrapProcessorFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "A processor component fault has been cleared."
--  Keywords for HP SIM integration
--#TYPE       "A processor component fault has been cleared."
--#SUMMARY    "A processor component fault has been cleared."
--#ARGUMENTS  {}
--#SEVERITY   INFORMATIONAL
    ::= { sunHwTrapPrefix 66 }

sunHwTrapProcessorError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A processor sensor has detected an error."
--  Keywords for HP SIM integration
--#TYPE       "A processor sensor has detected an error."
--#SUMMARY    "A processor sensor has detected an error."
--#ARGUMENTS  {}
--#SEVERITY   MAJOR
    ::= { sunHwTrapPrefix 38 }

sunHwTrapProcessorOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A processor sensor has returned to its normal state."
--  Keywords for HP SIM integration
--#TYPE       "A processor sensor has returned to its normal state."
--#SUMMARY    "A processor sensor has returned to its normal state."
--#ARGUMENTS  {}
--#SEVERITY   INFORMATIONAL
    ::= { sunHwTrapPrefix 39 }

sunHwTrapMemoryFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A memory component is suspected of causing a fault."
--  Keywords for HP SIM integration
--#TYPE       "A memory component is suspected of causing a fault."
--#SUMMARY    "A memory component is suspected of causing a fault."
--#ARGUMENTS  {}
--#SEVERITY   MAJOR
    ::= { sunHwTrapPrefix 40 }

sunHwTrapMemoryFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "A memory component fault has been cleared."
--  Keywords for HP SIM integration
--#TYPE       "A memory component fault has been cleared."
--#SUMMARY    "A memory component fault has been cleared."
--#ARGUMENTS  {}
--#SEVERITY   INFORMATIONAL
    ::= { sunHwTrapPrefix 67 }

sunHwTrapMemoryError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A memory sensor has detected an error."
--  Keywords for HP SIM integration
--#TYPE       "A memory sensor has detected an error."
--#SUMMARY    "A memory sensor has detected an error."
--#ARGUMENTS  {}
--#SEVERITY   MAJOR
    ::= { sunHwTrapPrefix 41 }

sunHwTrapMemoryOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A memory sensor has returned to its normal state."
--  Keywords for HP SIM integration
--#TYPE       "A memory sensor has returned to its normal state."
--#SUMMARY    "A memory sensor has returned to its normal state."
--#ARGUMENTS  {}
--#SEVERITY   INFORMATIONAL
    ::= { sunHwTrapPrefix 42 }

sunHwTrapHardDriveFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A hard drive component is suspected of causing a fault."
--  Keywords for HP SIM integration
--#TYPE       "A hard drive component is suspected of causing a fault."
--#SUMMARY    "A hard drive component is suspected of causing a fault."
--#ARGUMENTS  {}
--#SEVERITY   MAJOR
    ::= { sunHwTrapPrefix 43 }

sunHwTrapHardDriveFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "A hard drive component fault has been cleared."
--  Keywords for HP SIM integration
--#TYPE       "A hard drive component fault has been cleared."
--#SUMMARY    "A hard drive component fault has been cleared."
--#ARGUMENTS  {}
--#SEVERITY   INFORMATIONAL
    ::= { sunHwTrapPrefix 68 }

sunHwTrapHardDriveError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A hard drive sensor has detected an error."
--  Keywords for HP SIM integration
--#TYPE       "A hard drive sensor has detected an error."
--#SUMMARY    "A hard drive sensor has detected an error."
--#ARGUMENTS  {}
--#SEVERITY   MAJOR
    ::= { sunHwTrapPrefix 44 }

sunHwTrapHardDriveOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A hard drive sensor has returned to its normal state."
--  Keywords for HP SIM integration
--#TYPE       "A hard drive sensor has returned to its normal state."
--#SUMMARY    "A hard drive sensor has returned to its normal state."
--#ARGUMENTS  {}
--#SEVERITY   INFORMATIONAL
    ::= { sunHwTrapPrefix 45 }

sunHwTrapIOFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A component in the IO subsystem is suspected of causing a fault."
--  Keywords for HP SIM integration
--#TYPE       "A component in the IO subsystem is suspected of causing a fault."
--#SUMMARY    "A component in the IO subsystem is suspected of causing a fault."
--#ARGUMENTS  {}
--#SEVERITY   MAJOR
    ::= { sunHwTrapPrefix 46 }

sunHwTrapIOFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "An IO subsystem component fault has been cleared."
--  Keywords for HP SIM integration
--#TYPE       "An IO subsystem component fault has been cleared."
--#SUMMARY    "An IO subsystem component fault has been cleared."
--#ARGUMENTS  {}
--#SEVERITY   INFORMATIONAL
    ::= { sunHwTrapPrefix 69 }

sunHwTrapIOError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "An IO sensor has detected an error."
--  Keywords for HP SIM integration
--#TYPE       "An IO sensor has detected an error."
--#SUMMARY    "An IO sensor has detected an error."
--#ARGUMENTS  {}
--#SEVERITY   MAJOR
    ::= { sunHwTrapPrefix 47 }

sunHwTrapIOOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "An IO sensor has returned to its normal state."
--  Keywords for HP SIM integration
--#TYPE       "An IO sensor has returned to its normal state."
--#SUMMARY    "An IO sensor has returned to its normal state."
--#ARGUMENTS  {}
--#SEVERITY   INFORMATIONAL
    ::= { sunHwTrapPrefix 48 }

sunHwTrapSlotOrConnectorFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A slot or connector component is suspected of causing a fault."
--  Keywords for HP SIM integration
--#TYPE       "A slot or connector component is suspected of causing a fault."
--#SUMMARY    "A slot or connector component is suspected of causing a fault."
--#ARGUMENTS  {}
--#SEVERITY   MAJOR
    ::= { sunHwTrapPrefix 49 }

sunHwTrapSlotOrConnectorFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "A slot or connector component fault has been cleared."
--  Keywords for HP SIM integration
--#TYPE       "A slot or connector component fault has been cleared."
--#SUMMARY    "A slot or connector component fault has been cleared."
--#ARGUMENTS  {}
--#SEVERITY   INFORMATIONAL
    ::= { sunHwTrapPrefix 70 }

sunHwTrapSlotOrConnectorError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A sensor associated with a slot or connector has detected an error."
--  Keywords for HP SIM integration
--#TYPE       "A sensor associated with a slot or connector has detected an error."
--#SUMMARY    "A sensor associated with a slot or connector has detected an error."
--#ARGUMENTS  {}
--#SEVERITY   MAJOR
    ::= { sunHwTrapPrefix 50 }

sunHwTrapSlotOrConnectorOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A sensor associated with a slot or connector has returned
         to its normal state."
--  Keywords for HP SIM integration
--#TYPE       "A sensor associated with a slot or connector has returned to its normal state."
--#SUMMARY    "A sensor associated with a slot or connector has returned to its normal state."
--#ARGUMENTS  {}
--#SEVERITY   INFORMATIONAL
    ::= { sunHwTrapPrefix 51 }

sunHwTrapComponentFault NOTIFICATION-TYPE
    OBJECTS { sunHwTrapSystemIdentifier,
              sunHwTrapChassisId,
              sunHwTrapProductName,
              sunHwTrapSuspectComponentName,
              sunHwTrapFaultClass,
              sunHwTrapFaultCertainty,
              sunHwTrapFaultMessageID,
              sunHwTrapFaultUUID,
              sunHwTrapAssocObjectId,
              sunHwTrapAdditionalInfo
    }
    STATUS    current
    DESCRIPTION
        "A component is suspected of causing a fault. This generic 'component'
         trap is generated when the SNMP agent does not recognize the component
         type."
--  Keywords for HP SIM integration
--#TYPE       "A component is suspected of causing a fault. This generic 'component' trap is generated when the SNMP agent does not recognize the component type."
--#SUMMARY    "A component is suspected of causing a fault. This generic 'component' trap is generated when the SNMP agent does not recognize the component type."
--#ARGUMENTS  {}
--#SEVERITY   MAJOR
    ::= { sunHwTrapPrefix 52 }

sunHwTrapComponentFaultCleared NOTIFICATION-TYPE
    OBJECTS { sunHwTrapSystemIdentifier,
              sunHwTrapChassisId,
              sunHwTrapProductName,
              sunHwTrapComponentName,
              sunHwTrapAssocObjectId,
              sunHwTrapAdditionalInfo
    }
    STATUS    current
    DESCRIPTION
        "A component fault has been cleared. This generic 'component'
         trap is generated when the SNMP agent does not recognize the component
         type."
--  Keywords for HP SIM integration
--#TYPE       "A component fault has been cleared. This generic 'component' trap is generated when the SNMP agent does not recognize the component type."
--#SUMMARY    "A component fault has been cleared. This generic 'component' trap is generated when the SNMP agent does not recognize the component type."
--#ARGUMENTS  {}
--#SEVERITY   INFORMATIONAL
    ::= { sunHwTrapPrefix 71 }

sunHwTrapComponentError NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A sensor has detected an error. This generic 'component' trap is
         generated when the SNMP agent does not recognize the component type."
--  Keywords for HP SIM integration
--#TYPE       "A sensor has detected an error. This generic 'component' trap is generated when the SNMP agent does not recognize the component type."
--#SUMMARY    "A sensor has detected an error. This generic 'component' trap is generated when the SNMP agent does not recognize the component type."
--#ARGUMENTS  {}
--#SEVERITY   MAJOR
    ::= { sunHwTrapPrefix 53 }

sunHwTrapComponentOk NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "A sensor has returned to its normal state. This generic 'component'
         trap is generated when the SNMP agent does not recognize the component
         type."
--  Keywords for HP SIM integration
--#TYPE       "A sensor has returned to its normal state. This generic 'component' trap is generated when the SNMP agent does not recognize the component type."
--#SUMMARY    "A sensor has returned to its normal state. This generic 'component' trap is generated when the SNMP agent does not recognize the component type."
--#ARGUMENTS  {}
--#SEVERITY   INFORMATIONAL
    ::= { sunHwTrapPrefix 54 }

sunHwTrapFruInserted NOTIFICATION-TYPE
    OBJECTS { sunHwTrapSystemIdentifier,
              sunHwTrapChassisId,
              sunHwTrapProductName,
              sunHwTrapComponentName,
              sunHwTrapAssocObjectId
    }
    STATUS    current
    DESCRIPTION
        "A field replaceable unit has been inserted into the system."
--  Keywords for HP SIM integration
--#TYPE       "A field replaceable unit has been inserted into the system."
--#SUMMARY    "A field replaceable unit has been inserted into the system."
--#ARGUMENTS  {}
--#SEVERITY   INFORMATIONAL
    ::= { sunHwTrapPrefix 55 }

sunHwTrapFruRemoved NOTIFICATION-TYPE
    OBJECTS { sunHwTrapSystemIdentifier,
              sunHwTrapChassisId,
              sunHwTrapProductName,
              sunHwTrapComponentName,
              sunHwTrapAssocObjectId
    }
    STATUS    current
    DESCRIPTION
        "A field replaceable unit has been removed from the system."
--  Keywords for HP SIM integration
--#TYPE       "A field replaceable unit has been removed from the system."
--#SUMMARY    "A field replaceable unit has been removed from the system."
--#ARGUMENTS  {}
--#SEVERITY   INFORMATIONAL
    ::= { sunHwTrapPrefix 56 }

sunHwTrapComponentDisabled NOTIFICATION-TYPE
    OBJECTS { sunHwTrapSystemIdentifier,
              sunHwTrapChassisId,
              sunHwTrapProductName,
              sunHwTrapComponentName,
              sunHwTrapDisableReason,
              sunHwTrapAdditionalInfo,
              sunHwTrapAssocObjectId
    }
    STATUS    current
    DESCRIPTION
        "The component operational state has changed or is changing
         to disabled."
--  Keywords for HP SIM integration
--#TYPE       "The component operational state has changed or is changing to disabled."
--#SUMMARY    "The component operational state has changed or is changing to disabled."
--#ARGUMENTS  {}
--#SEVERITY   INFORMATIONAL
    ::= { sunHwTrapPrefix 57 }

sunHwTrapComponentEnabled NOTIFICATION-TYPE
    OBJECTS { sunHwTrapSystemIdentifier,
              sunHwTrapChassisId,
              sunHwTrapProductName,
              sunHwTrapComponentName,
              sunHwTrapAdditionalInfo,
              sunHwTrapAssocObjectId
    }
    STATUS    current
    DESCRIPTION
        "The component operational state has changed or is changing
         to enabled."
--  Keywords for HP SIM integration
--#TYPE       "The component operational state has changed or is changing to enabled."
--#SUMMARY    "The component operational state has changed or is changing to enabled."
--#ARGUMENTS  {}
--#SEVERITY   INFORMATIONAL
    ::= { sunHwTrapPrefix 58 }

sunHwTrapPreOSError NOTIFICATION-TYPE
    OBJECTS { sunHwTrapSystemIdentifier,
              sunHwTrapChassisId,
              sunHwTrapProductName,
              sunHwTrapAdditionalInfo
    }
    STATUS    current
    DESCRIPTION
        "An error has been detected in the period before the operating
         system has taken control of the system."
--  Keywords for HP SIM integration
--#TYPE       "An error has been detected in the period before the operating system has taken control of the system."
--#SUMMARY    "An error has been detected in the period before the operating system has taken control of the system."
--#ARGUMENTS  {}
--#SEVERITY   INFORMATIONAL
    ::= { sunHwTrapPrefix 59 }

sunHwTrapHAStateChange NOTIFICATION-TYPE
    OBJECTS { sunHwTrapSystemIdentifier,
              sunHwTrapChassisId,
              sunHwTrapProductName,
              sunHwTrapNewHAState,
              sunHwTrapOldHAState,
              sunHwTrapAdditionalInfo
    }
    STATUS    current
    DESCRIPTION
        "The high availability component identified by sunHwTrapSystemIdentifier
         has changed state."
--  Keywords for HP SIM integration
--#TYPE       "The high availability component identified by sunHwTrapSystemIdentifier has changed state."
--#SUMMARY    "The high availability component identified by sunHwTrapSystemIdentifier has changed state."
--#ARGUMENTS  {}
--#SEVERITY   INFORMATIONAL
    ::= { sunHwTrapPrefix 60 }

sunHwTrapSecurityIntrusion NOTIFICATION-TYPE
    OBJECTS { sunHwTrapSystemIdentifier,
              sunHwTrapChassisId,
              sunHwTrapProductName,
              sunHwTrapAdditionalInfo
    }
    STATUS    current
    DESCRIPTION
        "An intrusion sensor has detected that someone may have physically
         tampered with the system."
--  Keywords for HP SIM integration
--#TYPE       "An intrusion sensor has detected that someone may have physically tampered with the system."
--#SUMMARY    "An intrusion sensor has detected that someone may have physically tampered with the system."
--#ARGUMENTS  {}
--#SEVERITY   MAJOR
    ::= { sunHwTrapPrefix 61 }

sunHwTrapHardDriveStatus NOTIFICATION-TYPE
    OBJECTS { sunHwTrapSystemIdentifier,
              sunHwTrapChassisId,
              sunHwTrapProductName,
              sunHwTrapComponentName,
              sunHwTrapHardDriveState
    }
    STATUS    current
    DESCRIPTION
        "The hard drive identified by sunHwTrapComponentName has changed state."
--  Keywords for HP SIM integration
--#TYPE       "The hard drive identified by sunHwTrapComponentName has changed state."
--#SUMMARY    "The hard drive identified by sunHwTrapComponentName has changed state."
--#ARGUMENTS  {}
--#SEVERITY   INFORMATIONAL
    ::= { sunHwTrapPrefix 62 }

sunHwTrapTestTrap NOTIFICATION-TYPE
    OBJECTS { sunHwTrapSystemIdentifier,
              sunHwTrapChassisId,
              sunHwTrapProductName,
              sunHwTrapTestMessage
    }
    STATUS    current
    DESCRIPTION
        "This is a test trap"
--  Keywords for HP SIM integration
--#TYPE       "This is a test trap"
--#SUMMARY    "This is a test trap"
--#ARGUMENTS  {}
--#SEVERITY   INFORMATIONAL
    ::= { sunHwTrapPrefix 63 }

sunHwTrapPowerConsumptionThresholdExceeded NOTIFICATION-TYPE 
    OBJECTS { sunHwTrapSystemIdentifier, 
              sunHwTrapChassisId, 
              sunHwTrapProductName, 
              sunHwTrapComponentName,
              sunHwTrapThresholdType, 
              sunHwTrapThresholdValue, 
              sunHwTrapSensorValue, 
              sunHwTrapAdditionalInfo, 
              sunHwTrapAssocObjectId,
              sunHwTrapSeverity 
    } 
    STATUS    current 
    DESCRIPTION 
        "A power consumption threshold has been exceeded." 
--  Keywords for HP SIM integration
--#TYPE       "A power consumption threshold has been exceeded."
--#SUMMARY    "A power consumption threshold has been exceeded."
--#ARGUMENTS  {}
--#SEVERITY   INFORMATIONAL
    ::= { sunHwTrapPrefix 72 } 

sunHwTrapPowerConsumptionThresholdDeasserted NOTIFICATION-TYPE 
    OBJECTS { sunHwTrapSystemIdentifier, 
              sunHwTrapChassisId, 
              sunHwTrapProductName,
              sunHwTrapThresholdType, 
              sunHwTrapThresholdValue, 
              sunHwTrapSensorValue, 
              sunHwTrapAdditionalInfo, 
              sunHwTrapSeverity 
    }
    STATUS    current 
    DESCRIPTION 
        "A power consumption threshold has been deasserted." 
--  Keywords for HP SIM integration
--#TYPE       "A power consumption threshold has been deasserted."
--#SUMMARY    "A power consumption threshold has been deasserted."
--#ARGUMENTS  {}
--#SEVERITY   INFORMATIONAL
    ::= { sunHwTrapPrefix 73 } 

--
-- Object Groups
--

sunHwTrapNotificationObjectGroup OBJECT-GROUP
    OBJECTS {
        sunHwTrapSystemIdentifier,
        sunHwTrapComponentName,
        sunHwTrapThresholdType,
        sunHwTrapThresholdValue,
        sunHwTrapSensorValue,
        sunHwTrapSuspectComponentName,
        sunHwTrapFaultClass,
        sunHwTrapFaultCertainty,
        sunHwTrapAdditionalInfo,
        sunHwTrapAssocObjectId,
        sunHwTrapNewHAState,
        sunHwTrapOldHAState,
        sunHwTrapSeverity,
        sunHwTrapChassisId,
        sunHwTrapProductName,
        sunHwTrapHardDriveState,
        sunHwTrapFaultMessageID,
        sunHwTrapFaultUUID,
        sunHwTrapDisableReason,
        sunHwTrapTestMessage
    }
    STATUS current
    DESCRIPTION
        "The collection of objects used in notifications."
    ::= { sunHwTrapObjectGroups 2 }

--
-- Notification Groups
--

sunHwTrapNotificationsGroup NOTIFICATION-GROUP
    NOTIFICATIONS {
        sunHwTrapVoltageFatalThresholdExceeded,
        sunHwTrapVoltageFatalThresholdDeasserted,
        sunHwTrapVoltageCritThresholdExceeded,
        sunHwTrapVoltageCritThresholdDeasserted,
        sunHwTrapVoltageNonCritThresholdExceeded,
        sunHwTrapVoltageOk,
        sunHwTrapTempFatalThresholdExceeded,
        sunHwTrapTempFatalThresholdDeasserted,
        sunHwTrapTempCritThresholdExceeded,
        sunHwTrapTempCritThresholdDeasserted,
        sunHwTrapTempNonCritThresholdExceeded,
        sunHwTrapTempOk,
        sunHwTrapElectricalCurrentFatalThresholdExceeded,
        sunHwTrapElectricalCurrentFatalThresholdDeasserted,
        sunHwTrapElectricalCurrentCritThresholdExceeded,
        sunHwTrapElectricalCurrentCritThresholdDeasserted,
        sunHwTrapElectricalCurrentNonCritThresholdExceeded,
        sunHwTrapElectricalCurrentOk,
        sunHwTrapFanSpeedFatalThresholdExceeded,
        sunHwTrapFanSpeedFatalThresholdDeasserted,
        sunHwTrapFanSpeedCritThresholdExceeded,
        sunHwTrapFanSpeedCritThresholdDeasserted,
        sunHwTrapFanSpeedNonCritThresholdExceeded,
        sunHwTrapFanSpeedOk,
        sunHwTrapSensorFatalThresholdExceeded,
        sunHwTrapSensorFatalThresholdDeasserted,
        sunHwTrapSensorCritThresholdExceeded,
        sunHwTrapSensorCritThresholdDeasserted,
        sunHwTrapSensorNonCritThresholdExceeded,
        sunHwTrapSensorThresholdOk,
        sunHwTrapPowerSupplyFault,
        sunHwTrapPowerSupplyFaultCleared,
        sunHwTrapPowerSupplyError,
        sunHwTrapPowerSupplyOk,
        sunHwTrapFanFault,
        sunHwTrapFanFaultCleared,
        sunHwTrapFanError,
        sunHwTrapFanOk,
        sunHwTrapProcessorFault,
        sunHwTrapProcessorFaultCleared,
        sunHwTrapProcessorError,
        sunHwTrapProcessorOk,
        sunHwTrapMemoryFault,
        sunHwTrapMemoryFaultCleared,
        sunHwTrapMemoryError,
        sunHwTrapMemoryOk,
        sunHwTrapHardDriveFault,
        sunHwTrapHardDriveFaultCleared,
        sunHwTrapHardDriveError,
        sunHwTrapHardDriveOk,
        sunHwTrapIOFault,
        sunHwTrapIOFaultCleared,
        sunHwTrapIOError,
        sunHwTrapIOOk,
        sunHwTrapSlotOrConnectorFault,
        sunHwTrapSlotOrConnectorFaultCleared,
        sunHwTrapSlotOrConnectorError,
        sunHwTrapSlotOrConnectorOk,
        sunHwTrapComponentFault,
        sunHwTrapComponentFaultCleared,
        sunHwTrapComponentError,
        sunHwTrapComponentOk,
        sunHwTrapFruInserted,
        sunHwTrapFruRemoved,
        sunHwTrapComponentDisabled,
        sunHwTrapComponentEnabled,
        sunHwTrapPreOSError,
        sunHwTrapHAStateChange,
        sunHwTrapSecurityIntrusion,
        sunHwTrapHardDriveStatus,
        sunHwTrapTestTrap,
        sunHwTrapPowerConsumptionThresholdExceeded,
        sunHwTrapPowerConsumptionThresholdDeasserted
    }
    STATUS current
    DESCRIPTION
        "The collection of notifications used to indicate faults, errors,
         and other conditions related to HW components in the system."
    ::= { sunHwTrapNotifGroups 1 }

END

#
#
#
#
MIB: SUN-HW-TRAP-MIB (file:/tmp/ilom-mibs_6220/6220_SUN-HW-TRAP-MIB.mib) converted on Tue Jun  4 15:10:25 2013 using snmpttconvertmib v1.3
#
#
#
EVENT sunHwTrapVoltageFatalThresholdExceeded .1.3.6.1.4.1.42.2.175.103.2.0.1 "Status Events" CRITICAL
FORMAT A voltage sensor has reported that its value has gone above an upper fatal threshold setting or below a lower fatal threshold setting. The sunHwTrapThresholdType object indicates whether the threshold was an upper or lower.: A voltage sensor has reported that its value has gone above an upper fatal threshold setting or below a lower fatal threshold setting. The sunHwTrapThresholdType object indicates whether the threshold was an upper or lower.
SDESC
A voltage sensor has reported that its value has gone above an upper
fatal threshold setting or below a lower fatal threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapVoltageFatalThresholdDeasserted .1.3.6.1.4.1.42.2.175.103.2.0.2 "Status Events" INFORMATIONAL
FORMAT A voltage sensor has reported that its value has gone below an upper fatal threshold setting or above a lower fatal threshold setting. The sunHwTrapThresholdType object indicates whether the threshold was an upper or lower.: A voltage sensor has reported that its value has gone below an upper fatal threshold setting or above a lower fatal threshold setting.  The sunHwTrapThresholdType object indicates whether the threshold was an upper or lower.
SDESC
A voltage sensor has reported that its value has gone below an upper
fatal threshold setting or above a lower fatal threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapVoltageCritThresholdExceeded .1.3.6.1.4.1.42.2.175.103.2.0.3 "Status Events" MAJOR
FORMAT A voltage sensor has reported that its value has gone above an upper critical threshold setting or below a lower critical threshold setting. The sunHwTrapThresholdType object indicates whether the threshold was an upper or lower.: A voltage sensor has reported that its value has gone above an upper critical threshold setting or below a lower critical threshold setting. The sunHwTrapThresholdType object indicates whether the threshold was an upper or lower.
SDESC
A voltage sensor has reported that its value has gone above an upper
critical threshold setting or below a lower critical threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapVoltageCritThresholdDeasserted .1.3.6.1.4.1.42.2.175.103.2.0.4 "Status Events" INFORMATIONAL
FORMAT A voltage sensor has reported that its value has gone below an upper critical threshold setting or above a lower critical threshold setting. The sunHwTrapThresholdType object indicates whether the threshold was an upper or lower.: A voltage sensor has reported that its value has gone below an upper critical threshold setting or above a lower critical threshold setting. The sunHwTrapThresholdType object indicates whether the threshold was an upper or lower.
SDESC
A voltage sensor has reported that its value has gone below an upper
critical threshold setting or above a lower critical threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapVoltageNonCritThresholdExceeded .1.3.6.1.4.1.42.2.175.103.2.0.5 "Status Events" MINOR
FORMAT A voltage sensor has reported that its value has gone above an upper non-critical threshold setting or below a lower non-critical threshold setting. The sunHwTrapThresholdType object indicates whether the threshold was an upper or lower.: A voltage sensor has reported that its value has gone above an upper non-critical threshold setting or below a lower non-critical threshold setting. The sunHwTrapThresholdType object indicates whether the threshold was an upper or lower.
SDESC
A voltage sensor has reported that its value has gone above an upper
non-critical threshold setting or below a lower non-critical threshold
setting. The sunHwTrapThresholdType object indicates whether the threshold
was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapVoltageOk .1.3.6.1.4.1.42.2.175.103.2.0.6 "Status Events" INFORMATIONAL
FORMAT A voltage sensor has reported that its value is in the normal operating range.: A voltage sensor has reported that its value is in the normal operating range.
SDESC
A voltage sensor has reported that its value is in the normal
operating range.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapTempFatalThresholdExceeded .1.3.6.1.4.1.42.2.175.103.2.0.7 "Status Events" CRITICAL
FORMAT A temperature sensor has reported that its value has gone above an upper fatal threshold setting or below a lower fatal threshold setting. The sunHwTrapThresholdType object indicates whether the threshold was an upper or lower.: A temperature sensor has reported that its value has gone above an upper fatal threshold setting or below a lower fatal threshold setting. The sunHwTrapThresholdType object indicates whether the threshold was an upper or lower.
SDESC
A temperature sensor has reported that its value has gone above an upper
fatal threshold setting or below a lower fatal threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapTempFatalThresholdDeasserted .1.3.6.1.4.1.42.2.175.103.2.0.8 "Status Events" INFORMATIONAL
FORMAT A temperature sensor has reported that its value has gone below an upper fatal threshold setting or above a lower fatal threshold setting. The sunHwTrapThresholdType object indicates whether the threshold was an upper or lower.: A temperature sensor has reported that its value has gone below an upper fatal threshold setting or above a lower fatal threshold setting. The sunHwTrapThresholdType object indicates whether the threshold was an upper or lower.
SDESC
A temperature sensor has reported that its value has gone below an
upper fatal threshold setting or above a lower fatal threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapTempCritThresholdExceeded .1.3.6.1.4.1.42.2.175.103.2.0.9 "Status Events" MAJOR
FORMAT A temperature sensor has reported that its value has gone above an upper critical threshold setting or below a lower critical threshold setting. The sunHwTrapThresholdType object indicates whether the threshold was an upper or lower.: A temperature sensor has reported that its value has gone above an upper critical threshold setting or below a lower critical threshold setting. The sunHwTrapThresholdType object indicates whether the threshold was an upper or lower.
SDESC
A temperature sensor has reported that its value has gone above an
upper critical threshold setting or below a lower critical threshold
setting. The sunHwTrapThresholdType object indicates whether the
threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapTempCritThresholdDeasserted .1.3.6.1.4.1.42.2.175.103.2.0.10 "Status Events" INFORMATIONAL
FORMAT A temperature sensor has reported that its value has gone below an upper critical threshold setting or above a lower critical threshold setting. The sunHwTrapThresholdType object indicates whether the threshold was an upper or lower.: A temperature sensor has reported that its value has gone below an upper critical threshold setting or above a lower critical threshold setting. The sunHwTrapThresholdType object indicates whether the threshold was an upper or lower.
SDESC
A temperature sensor has reported that its value has gone below an
upper critical threshold setting or above a lower critical threshold
setting. The sunHwTrapThresholdType object indicates whether the
threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapTempNonCritThresholdExceeded .1.3.6.1.4.1.42.2.175.103.2.0.11 "Status Events" MINOR
FORMAT A temperature sensor has reported that its value has gone above an upper non-critical threshold setting or below a lower non-critical threshold setting. The sunHwTrapThresholdType object indicates whether the threshold was an upper or lower.: A temperature sensor has reported that its value has gone above an upper non-critical threshold setting or below a lower non-critical threshold setting. The sunHwTrapThresholdType object indicates whether the threshold was an upper or lower.
SDESC
A temperature sensor has reported that its value has gone above an
upper non-critical threshold setting or below a lower non-critical
threshold setting. The sunHwTrapThresholdType object indicates whether
the threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapTempOk .1.3.6.1.4.1.42.2.175.103.2.0.12 "Status Events" INFORMATIONAL
FORMAT A temperature sensor has reported that its value is in the normal operating range.: A temperature sensor has reported that its value is in the normal operating range.
SDESC
A temperature sensor has reported that its value is in the normal
operating range.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapElectricalCurrentFatalThresholdExceeded .1.3.6.1.4.1.42.2.175.103.2.0.13 "Status Events" CRITICAL
FORMAT An electrical current sensor has reported that its value has gone above an upper fatal threshold setting or below a lower fatal threshold setting. The sunHwTrapThresholdType object indicates whether the threshold was an upper or lower.: An electrical current sensor has reported that its value has gone above an upper fatal threshold setting or below a lower fatal threshold setting. The sunHwTrapThresholdType object indicates whether the threshold was an upper or lower.
SDESC
An electrical current sensor has reported that its value has gone above
an upper fatal threshold setting or below a lower fatal threshold
setting. The sunHwTrapThresholdType object indicates whether the
threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapElectricalCurrentFatalThresholdDeasserted .1.3.6.1.4.1.42.2.175.103.2.0.14 "Status Events" INFORMATIONAL
FORMAT An electrical current sensor has reported that its value has gone below an upper fatal threshold setting or above a lower fatal threshold setting. The sunHwTrapThresholdType object indicates whether the threshold was an upper or lower.: An electrical current sensor has reported that its value has gone below an upper fatal threshold setting or above a lower fatal threshold setting. The sunHwTrapThresholdType object indicates whether the threshold was an upper or lower.
SDESC
An electrical current sensor has reported that its value has gone below
an upper fatal threshold setting or above a lower fatal threshold
setting. The sunHwTrapThresholdType object indicates whether the
threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapElectricalCurrentCritThresholdExceeded .1.3.6.1.4.1.42.2.175.103.2.0.15 "Status Events" MAJOR
FORMAT An electrical current sensor has reported that its value has gone above an upper critical threshold setting or below a lower critical threshold setting. The sunHwTrapThresholdType object indicates whether the threshold was an upper or lower.: An electrical current sensor has reported that its value has gone above an upper critical threshold setting or below a lower critical threshold setting. The sunHwTrapThresholdType object indicates whether the threshold was an upper or lower.
SDESC
An electrical current sensor has reported that its value has gone above
an upper critical threshold setting or below a lower critical threshold
setting. The sunHwTrapThresholdType object indicates whether the
threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapElectricalCurrentCritThresholdDeasserted .1.3.6.1.4.1.42.2.175.103.2.0.16 "Status Events" INFORMATIONAL
FORMAT An electrical current sensor has reported that its value has gone below an upper critical threshold setting or above a lower critical threshold setting. The sunHwTrapThresholdType object indicates whether the threshold was an upper or lower.: An electrical current sensor has reported that its value has gone below an upper critical threshold setting or above a lower critical threshold setting. The sunHwTrapThresholdType object indicates whether the threshold was an upper or lower.
SDESC
An electrical current sensor has reported that its value has gone below
an upper critical threshold setting or above a lower critical threshold
setting. The sunHwTrapThresholdType object indicates whether the
threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapElectricalCurrentNonCritThresholdExceeded .1.3.6.1.4.1.42.2.175.103.2.0.17 "Status Events" MINOR
FORMAT An electrical current sensor has reported that its value has gone above an upper non-critical threshold setting or below a lower non-critical threshold setting. The sunHwTrapThresholdType object indicates whether the threshold was an upper or lower.: An electrical current sensor has reported that its value has gone above an upper non-critical threshold setting or below a lower non-critical threshold setting. The sunHwTrapThresholdType object indicates whether the threshold was an upper or lower.
SDESC
An electrical current sensor has reported that its value has gone above
an upper non-critical threshold setting or below a lower non-critical
threshold setting. The sunHwTrapThresholdType object indicates whether
the threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapElectricalCurrentOk .1.3.6.1.4.1.42.2.175.103.2.0.18 "Status Events" INFORMATIONAL
FORMAT An electrical current sensor has reported that its value is in the normal operating range.: An electrical current sensor has reported that its value is in the normal operating range.
SDESC
An electrical current sensor has reported that its value is in
the normal operating range.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapFanSpeedFatalThresholdExceeded .1.3.6.1.4.1.42.2.175.103.2.0.19 "Status Events" CRITICAL
FORMAT A fan speed sensor has reported that its value has gone above an upper fatal threshold setting or below a lower fatal threshold setting. The sunHwTrapThresholdType object indicates whether the threshold was an upper or lower.: A fan speed sensor has reported that its value has gone above an upper fatal threshold setting or below a lower fatal threshold setting. The sunHwTrapThresholdType object indicates whether the threshold was an upper or lower.
SDESC
A fan speed sensor has reported that its value has gone above an upper
fatal threshold setting or below a lower fatal threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapFanSpeedFatalThresholdDeasserted .1.3.6.1.4.1.42.2.175.103.2.0.20 "Status Events" INFORMATIONAL
FORMAT A fan speed sensor has reported that its value has gone below an upper fatal threshold setting or above a lower fatal threshold setting. The sunHwTrapThresholdType object indicates whether the threshold was an upper or lower.: A fan speed sensor has reported that its value has gone below an upper fatal threshold setting or above a lower fatal threshold setting. The sunHwTrapThresholdType object indicates whether the threshold was an upper or lower.
SDESC
A fan speed sensor has reported that its value has gone below an upper
fatal threshold setting or above a lower fatal threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapFanSpeedCritThresholdExceeded .1.3.6.1.4.1.42.2.175.103.2.0.21 "Status Events" MAJOR
FORMAT A fan speed sensor has reported that its value has gone above an upper critical threshold setting or below a lower critical threshold setting. The sunHwTrapThresholdType object indicates whether the threshold was an upper or lower.: A fan speed sensor has reported that its value has gone above an upper critical threshold setting or below a lower critical threshold setting. The sunHwTrapThresholdType object indicates whether the threshold was an upper or lower.
SDESC
A fan speed sensor has reported that its value has gone above an upper
critical threshold setting or below a lower critical threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapFanSpeedCritThresholdDeasserted .1.3.6.1.4.1.42.2.175.103.2.0.22 "Status Events" INFORMATIONAL
FORMAT A fan speed sensor has reported that its value has gone below an upper critical threshold setting or above a lower critical threshold setting. The sunHwTrapThresholdType object indicates whether the threshold was an upper or lower.: A fan speed sensor has reported that its value has gone below an upper critical threshold setting or above a lower critical threshold setting. The sunHwTrapThresholdType object indicates whether the threshold was an upper or lower.
SDESC
A fan speed sensor has reported that its value has gone below an upper
critical threshold setting or above a lower critical threshold setting.
The sunHwTrapThresholdType object indicates whether the threshold was
an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapFanSpeedNonCritThresholdExceeded .1.3.6.1.4.1.42.2.175.103.2.0.23 "Status Events" MINOR
FORMAT A fan speed sensor has reported that its value has gone above an upper non-critical threshold setting or below a lower non-critical threshold setting. The sunHwTrapThresholdType object indicates whether the threshold was an upper or lower.: A fan speed sensor has reported that its value has gone above an upper non-critical threshold setting or below a lower non-critical threshold setting. The sunHwTrapThresholdType object indicates whether the threshold was an upper or lower.
SDESC
A fan speed sensor has reported that its value has gone above an upper
non-critical threshold setting or below a lower non-critical threshold
setting. The sunHwTrapThresholdType object indicates whether the
threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapFanSpeedOk .1.3.6.1.4.1.42.2.175.103.2.0.24 "Status Events" INFORMATIONAL
FORMAT A fan speed sensor has reported that its value is in the normal operating range.: A fan speed sensor has reported that its value is in the normal operating range.
SDESC
A fan speed sensor has reported that its value is in
the normal operating range.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapSensorFatalThresholdExceeded .1.3.6.1.4.1.42.2.175.103.2.0.25 "Status Events" CRITICAL
FORMAT A sensor has reported that its value has gone above an upper fatal threshold setting or below a lower fatal threshold setting. The  generic 'sensor' trap is generated when the SNMP agent does not recognize the component type. The sunHwTrapThresholdType object indicates whether the threshold was an upper or lower.: A sensor has reported that its value has gone above an upper fatal threshold setting or below a lower fatal threshold setting. The  generic 'sensor' trap is generated when the SNMP agent does not recognize the component type. The sunHwTrapThresholdType object indicates whether the threshold was an upper or lower.
SDESC
A sensor has reported that its value has gone above an upper fatal
threshold setting or below a lower fatal threshold setting. The 
generic 'sensor' trap is generated when the SNMP agent does not
recognize the component type. The sunHwTrapThresholdType object
indicates whether the threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapSensorFatalThresholdDeasserted .1.3.6.1.4.1.42.2.175.103.2.0.26 "Status Events" INFORMATIONAL
FORMAT A sensor has reported that its value has gone below an upper fatal threshold setting or above a lower fatal threshold setting. The generic 'sensor' trap is generated when the SNMP agent does not recognize the component type. The sunHwTrapThresholdType object indicates whether the threshold was an upper or lower.: A sensor has reported that its value has gone below an upper fatal threshold setting or above a lower fatal threshold setting. The generic 'sensor' trap is generated when the SNMP agent does not recognize the component type. The sunHwTrapThresholdType object indicates whether the threshold was an upper or lower.
SDESC
A sensor has reported that its value has gone below an upper fatal
threshold setting or above a lower fatal threshold setting. The
generic 'sensor' trap is generated when the SNMP agent does not
recognize the component type. The sunHwTrapThresholdType object
indicates whether the threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapSensorCritThresholdExceeded .1.3.6.1.4.1.42.2.175.103.2.0.27 "Status Events" MAJOR
FORMAT A sensor has reported that its value has gone above an upper critical threshold setting or below a lower critical threshold setting. The  generic 'sensor' trap is generated when the SNMP agent does not recognize the component type. The sunHwTrapThresholdType object indicates whether the threshold was an upper or lower.: A sensor has reported that its value has gone above an upper critical threshold setting or below a lower critical threshold setting. The  generic 'sensor' trap is generated when the SNMP agent does not recognize the component type. The sunHwTrapThresholdType object indicates whether the threshold was an upper or lower.
SDESC
A sensor has reported that its value has gone above an upper critical
threshold setting or below a lower critical threshold setting. The 
generic 'sensor' trap is generated when the SNMP agent does not
recognize the component type. The sunHwTrapThresholdType object
indicates whether the threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapSensorCritThresholdDeasserted .1.3.6.1.4.1.42.2.175.103.2.0.28 "Status Events" INFORMATIONAL
FORMAT A sensor has reported that its value has gone below an upper critical threshold setting or above a lower critical threshold setting. The generic 'sensor' trap is generated when the SNMP agent does not recognize the component type. The sunHwTrapThresholdType object indicates whether the threshold was an upper or lower.: A sensor has reported that its value has gone below an upper critical threshold setting or above a lower critical threshold setting. The generic 'sensor' trap is generated when the SNMP agent does not recognize the component type. The sunHwTrapThresholdType object indicates whether the threshold was an upper or lower.
SDESC
A sensor has reported that its value has gone below an upper critical
threshold setting or above a lower critical threshold setting. The
generic 'sensor' trap is generated when the SNMP agent does not
recognize the component type. The sunHwTrapThresholdType object
indicates whether the threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapSensorNonCritThresholdExceeded .1.3.6.1.4.1.42.2.175.103.2.0.29 "Status Events" MINOR
FORMAT A sensor has reported that its value has gone above an upper non-critical threshold setting or below a lower non-critical threshold setting. The generic 'sensor' trap is generated when the SNMP agent does not recognize the component type. The sunHwTrapThresholdType object indicates whether the threshold was an upper or lower.: A sensor has reported that its value has gone above an upper non-critical threshold setting or below a lower non-critical threshold setting. The generic 'sensor' trap is generated when the SNMP agent does not recognize the component type. The sunHwTrapThresholdType object indicates whether the threshold was an upper or lower.
SDESC
A sensor has reported that its value has gone above an upper
non-critical threshold setting or below a lower non-critical threshold
setting. The generic 'sensor' trap is generated when the SNMP agent
does not recognize the component type. The sunHwTrapThresholdType
object indicates whether the threshold was an upper or lower.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapSensorThresholdOk .1.3.6.1.4.1.42.2.175.103.2.0.30 "Status Events" INFORMATIONAL
FORMAT A sensor has reported that its value is in the normal operating range. The generic 'sensor' trap is generated when the SNMP agent does not recognize the component type.: A sensor has reported that its value is in the normal operating range. The generic 'sensor' trap is generated when the SNMP agent does not recognize the component type.
SDESC
A sensor has reported that its value is in the normal operating range.
The generic 'sensor' trap is generated when the SNMP agent does not
recognize the component type.
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapPowerSupplyFault .1.3.6.1.4.1.42.2.175.103.2.0.31 "Status Events" MAJOR
FORMAT A power supply component is suspected of causing a fault.: A power supply component is suspected of causing a fault.
SDESC
A power supply component is suspected of causing a fault.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapPowerSupplyFaultCleared .1.3.6.1.4.1.42.2.175.103.2.0.64 "Status Events" INFORMATIONAL
FORMAT A power supply component fault has been cleared.: A power supply component fault has been cleared.
SDESC
A power supply component fault has been cleared.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapPowerSupplyError .1.3.6.1.4.1.42.2.175.103.2.0.32 "Status Events" MAJOR
FORMAT A power supply sensor has detected an error.: A power supply sensor has detected an error.
SDESC
A power supply sensor has detected an error.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapPowerSupplyOk .1.3.6.1.4.1.42.2.175.103.2.0.33 "Status Events" INFORMATIONAL
FORMAT A power supply sensor has returned to its normal state.: A power supply sensor has returned to its normal state.
SDESC
A power supply sensor has returned to its normal state.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapFanFault .1.3.6.1.4.1.42.2.175.103.2.0.34 "Status Events" MAJOR
FORMAT A fan component is suspected of causing a fault.: A fan component is suspected of causing a fault.
SDESC
A fan component is suspected of causing a fault.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapFanFaultCleared .1.3.6.1.4.1.42.2.175.103.2.0.65 "Status Events" INFORMATIONAL
FORMAT A fan component fault has been cleared.: A fan component fault has been cleared.
SDESC
A fan component fault has been cleared.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapFanError .1.3.6.1.4.1.42.2.175.103.2.0.35 "Status Events" MAJOR
FORMAT A fan sensor has detected an error.: A fan sensor has detected an error.
SDESC
A fan sensor has detected an error.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapFanOk .1.3.6.1.4.1.42.2.175.103.2.0.36 "Status Events" INFORMATIONAL
FORMAT A fan sensor has returned to its normal state.: A fan sensor has returned to its normal state.
SDESC
A fan sensor has returned to its normal state.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapProcessorFault .1.3.6.1.4.1.42.2.175.103.2.0.37 "Status Events" MAJOR
FORMAT A processor component is suspected of causing a fault.: A processor component is suspected of causing a fault.
SDESC
A processor component is suspected of causing a fault.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapProcessorFaultCleared .1.3.6.1.4.1.42.2.175.103.2.0.66 "Status Events" INFORMATIONAL
FORMAT A processor component fault has been cleared.: A processor component fault has been cleared.
SDESC
A processor component fault has been cleared.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapProcessorError .1.3.6.1.4.1.42.2.175.103.2.0.38 "Status Events" MAJOR
FORMAT A processor sensor has detected an error.: A processor sensor has detected an error.
SDESC
A processor sensor has detected an error.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapProcessorOk .1.3.6.1.4.1.42.2.175.103.2.0.39 "Status Events" INFORMATIONAL
FORMAT A processor sensor has returned to its normal state.: A processor sensor has returned to its normal state.
SDESC
A processor sensor has returned to its normal state.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapMemoryFault .1.3.6.1.4.1.42.2.175.103.2.0.40 "Status Events" MAJOR
FORMAT A memory component is suspected of causing a fault.: A memory component is suspected of causing a fault.
SDESC
A memory component is suspected of causing a fault.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapMemoryFaultCleared .1.3.6.1.4.1.42.2.175.103.2.0.67 "Status Events" INFORMATIONAL
FORMAT A memory component fault has been cleared.: A memory component fault has been cleared.
SDESC
A memory component fault has been cleared.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapMemoryError .1.3.6.1.4.1.42.2.175.103.2.0.41 "Status Events" MAJOR
FORMAT A memory sensor has detected an error.: A memory sensor has detected an error.
SDESC
A memory sensor has detected an error.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapMemoryOk .1.3.6.1.4.1.42.2.175.103.2.0.42 "Status Events" INFORMATIONAL
FORMAT A memory sensor has returned to its normal state.: A memory sensor has returned to its normal state.
SDESC
A memory sensor has returned to its normal state.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapHardDriveFault .1.3.6.1.4.1.42.2.175.103.2.0.43 "Status Events" MAJOR
FORMAT A hard drive component is suspected of causing a fault.: A hard drive component is suspected of causing a fault.
SDESC
A hard drive component is suspected of causing a fault.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapHardDriveFaultCleared .1.3.6.1.4.1.42.2.175.103.2.0.68 "Status Events" INFORMATIONAL
FORMAT A hard drive component fault has been cleared.: A hard drive component fault has been cleared.
SDESC
A hard drive component fault has been cleared.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapHardDriveError .1.3.6.1.4.1.42.2.175.103.2.0.44 "Status Events" MAJOR
FORMAT A hard drive sensor has detected an error.: A hard drive sensor has detected an error.
SDESC
A hard drive sensor has detected an error.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapHardDriveOk .1.3.6.1.4.1.42.2.175.103.2.0.45 "Status Events" INFORMATIONAL
FORMAT A hard drive sensor has returned to its normal state.: A hard drive sensor has returned to its normal state.
SDESC
A hard drive sensor has returned to its normal state.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapIOFault .1.3.6.1.4.1.42.2.175.103.2.0.46 "Status Events" MAJOR
FORMAT A component in the IO subsystem is suspected of causing a fault.: A component in the IO subsystem is suspected of causing a fault.
SDESC
A component in the IO subsystem is suspected of causing a fault.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapIOFaultCleared .1.3.6.1.4.1.42.2.175.103.2.0.69 "Status Events" INFORMATIONAL
FORMAT An IO subsystem component fault has been cleared.: An IO subsystem component fault has been cleared.
SDESC
An IO subsystem component fault has been cleared.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapIOError .1.3.6.1.4.1.42.2.175.103.2.0.47 "Status Events" MAJOR
FORMAT An IO sensor has detected an error.: An IO sensor has detected an error.
SDESC
An IO sensor has detected an error.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapIOOk .1.3.6.1.4.1.42.2.175.103.2.0.48 "Status Events" INFORMATIONAL
FORMAT An IO sensor has returned to its normal state.: An IO sensor has returned to its normal state.
SDESC
An IO sensor has returned to its normal state.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapSlotOrConnectorFault .1.3.6.1.4.1.42.2.175.103.2.0.49 "Status Events" MAJOR
FORMAT A slot or connector component is suspected of causing a fault.: A slot or connector component is suspected of causing a fault.
SDESC
A slot or connector component is suspected of causing a fault.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapSlotOrConnectorFaultCleared .1.3.6.1.4.1.42.2.175.103.2.0.70 "Status Events" INFORMATIONAL
FORMAT A slot or connector component fault has been cleared.: A slot or connector component fault has been cleared.
SDESC
A slot or connector component fault has been cleared.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapSlotOrConnectorError .1.3.6.1.4.1.42.2.175.103.2.0.50 "Status Events" MAJOR
FORMAT A sensor associated with a slot or connector has detected an error.: A sensor associated with a slot or connector has detected an error.
SDESC
A sensor associated with a slot or connector has detected an error.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapSlotOrConnectorOk .1.3.6.1.4.1.42.2.175.103.2.0.51 "Status Events" INFORMATIONAL
FORMAT A sensor associated with a slot or connector has returned to its normal state.: A sensor associated with a slot or connector has returned to its normal state.
SDESC
A sensor associated with a slot or connector has returned
to its normal state.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapComponentFault .1.3.6.1.4.1.42.2.175.103.2.0.52 "Status Events" MAJOR
FORMAT A component is suspected of causing a fault. This generic 'component' trap is generated when the SNMP agent does not recognize the component type.: A component is suspected of causing a fault. This generic 'component' trap is generated when the SNMP agent does not recognize the component type.
SDESC
A component is suspected of causing a fault. This generic 'component'
trap is generated when the SNMP agent does not recognize the component
type.
--  Keywords for HP SIM integration
Variables:
  1: sunHwTrapSystemIdentifier
  2: sunHwTrapChassisId
  3: sunHwTrapProductName
  4: sunHwTrapSuspectComponentName
  5: sunHwTrapFaultClass
  6: sunHwTrapFaultCertainty
  7: sunHwTrapFaultMessageID
  8: sunHwTrapFaultUUID
  9: sunHwTrapAssocObjectId
  10: sunHwTrapAdditionalInfo
EDESC
#
#
#
EVENT sunHwTrapComponentFaultCleared .1.3.6.1.4.1.42.2.175.103.2.0.71 "Status Events" INFORMATIONAL
FORMAT A component fault has been cleared. This generic 'component' trap is generated when the SNMP agent does not recognize the component type.: A component fault has been cleared. This generic 'component' trap is generated when the SNMP agent does not recognize the component type.
SDESC
A component fault has been cleared. This generic 'component'
trap is generated when the SNMP agent does not recognize the component
type.
--  Keywords for HP SIM integration
Variables:
  1: sunHwTrapSystemIdentifier
  2: sunHwTrapChassisId
  3: sunHwTrapProductName
  4: sunHwTrapComponentName
  5: sunHwTrapAssocObjectId
  6: sunHwTrapAdditionalInfo
EDESC
#
#
#
EVENT sunHwTrapComponentError .1.3.6.1.4.1.42.2.175.103.2.0.53 "Status Events" MAJOR
FORMAT A sensor has detected an error. This generic 'component' trap is generated when the SNMP agent does not recognize the component type.: A sensor has detected an error. This generic 'component' trap is generated when the SNMP agent does not recognize the component type.
SDESC
A sensor has detected an error. This generic 'component' trap is
generated when the SNMP agent does not recognize the component type.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapComponentOk .1.3.6.1.4.1.42.2.175.103.2.0.54 "Status Events" INFORMATIONAL
FORMAT A sensor has returned to its normal state. This generic 'component' trap is generated when the SNMP agent does not recognize the component type.: A sensor has returned to its normal state. This generic 'component' trap is generated when the SNMP agent does not recognize the component type.
SDESC
A sensor has returned to its normal state. This generic 'component'
trap is generated when the SNMP agent does not recognize the component
type.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapFruInserted .1.3.6.1.4.1.42.2.175.103.2.0.55 "Status Events" INFORMATIONAL
FORMAT A field replaceable unit has been inserted into the system.: A field replaceable unit has been inserted into the system.
SDESC
A field replaceable unit has been inserted into the system.
--  Keywords for HP SIM integration
Variables:
  1: sunHwTrapSystemIdentifier
  2: sunHwTrapChassisId
  3: sunHwTrapProductName
  4: sunHwTrapComponentName
  5: sunHwTrapAssocObjectId
EDESC
#
#
#
EVENT sunHwTrapFruRemoved .1.3.6.1.4.1.42.2.175.103.2.0.56 "Status Events" INFORMATIONAL
FORMAT A field replaceable unit has been removed from the system.: A field replaceable unit has been removed from the system.
SDESC
A field replaceable unit has been removed from the system.
--  Keywords for HP SIM integration
Variables:
  1: sunHwTrapSystemIdentifier
  2: sunHwTrapChassisId
  3: sunHwTrapProductName
  4: sunHwTrapComponentName
  5: sunHwTrapAssocObjectId
EDESC
#
#
#
EVENT sunHwTrapComponentDisabled .1.3.6.1.4.1.42.2.175.103.2.0.57 "Status Events" INFORMATIONAL
FORMAT The component operational state has changed or is changing to disabled.: The component operational state has changed or is changing to disabled.
SDESC
The component operational state has changed or is changing
to disabled.
--  Keywords for HP SIM integration
Variables:
  1: sunHwTrapSystemIdentifier
  2: sunHwTrapChassisId
  3: sunHwTrapProductName
  4: sunHwTrapComponentName
  5: sunHwTrapDisableReason
  6: sunHwTrapAdditionalInfo
  7: sunHwTrapAssocObjectId
EDESC
#
#
#
EVENT sunHwTrapComponentEnabled .1.3.6.1.4.1.42.2.175.103.2.0.58 "Status Events" INFORMATIONAL
FORMAT The component operational state has changed or is changing to enabled.: The component operational state has changed or is changing to enabled.
SDESC
The component operational state has changed or is changing
to enabled.
--  Keywords for HP SIM integration
Variables:
  1: sunHwTrapSystemIdentifier
  2: sunHwTrapChassisId
  3: sunHwTrapProductName
  4: sunHwTrapComponentName
  5: sunHwTrapAdditionalInfo
  6: sunHwTrapAssocObjectId
EDESC
#
#
#
EVENT sunHwTrapPreOSError .1.3.6.1.4.1.42.2.175.103.2.0.59 "Status Events" INFORMATIONAL
FORMAT An error has been detected in the period before the operating system has taken control of the system.: An error has been detected in the period before the operating system has taken control of the system.
SDESC
An error has been detected in the period before the operating
system has taken control of the system.
--  Keywords for HP SIM integration
Variables:
  1: sunHwTrapSystemIdentifier
  2: sunHwTrapChassisId
  3: sunHwTrapProductName
  4: sunHwTrapAdditionalInfo
EDESC
#
#
#
EVENT sunHwTrapHAStateChange .1.3.6.1.4.1.42.2.175.103.2.0.60 "Status Events" INFORMATIONAL
FORMAT The high availability component identified by sunHwTrapSystemIdentifier has changed state.: The high availability component identified by sunHwTrapSystemIdentifier has changed state.
SDESC
The high availability component identified by sunHwTrapSystemIdentifier
has changed state.
--  Keywords for HP SIM integration
Variables:
  1: sunHwTrapSystemIdentifier
  2: sunHwTrapChassisId
  3: sunHwTrapProductName
  4: sunHwTrapNewHAState
  5: sunHwTrapOldHAState
  6: sunHwTrapAdditionalInfo
EDESC
#
#
#
EVENT sunHwTrapSecurityIntrusion .1.3.6.1.4.1.42.2.175.103.2.0.61 "Status Events" MAJOR
FORMAT An intrusion sensor has detected that someone may have physically tampered with the system.: An intrusion sensor has detected that someone may have physically tampered with the system.
SDESC
An intrusion sensor has detected that someone may have physically
tampered with the system.
--  Keywords for HP SIM integration
Variables:
  1: sunHwTrapSystemIdentifier
  2: sunHwTrapChassisId
  3: sunHwTrapProductName
  4: sunHwTrapAdditionalInfo
EDESC
#
#
#
EVENT sunHwTrapHardDriveStatus .1.3.6.1.4.1.42.2.175.103.2.0.62 "Status Events" INFORMATIONAL
FORMAT The hard drive identified by sunHwTrapComponentName has changed state.: The hard drive identified by sunHwTrapComponentName has changed state.
SDESC
The hard drive identified by sunHwTrapComponentName has changed state.
--  Keywords for HP SIM integration
Variables:
  1: sunHwTrapSystemIdentifier
  2: sunHwTrapChassisId
  3: sunHwTrapProductName
  4: sunHwTrapComponentName
  5: sunHwTrapHardDriveState
EDESC
#
#
#
EVENT sunHwTrapTestTrap .1.3.6.1.4.1.42.2.175.103.2.0.63 "Status Events" INFORMATIONAL
FORMAT This is a test trap: This is a test trap
SDESC
This is a test trap
--  Keywords for HP SIM integration
Variables:
  1: sunHwTrapSystemIdentifier
  2: sunHwTrapChassisId
  3: sunHwTrapProductName
  4: sunHwTrapTestMessage
EDESC
#
#
#
EVENT sunHwTrapPowerConsumptionThresholdExceeded .1.3.6.1.4.1.42.2.175.103.2.0.72 "Status Events" INFORMATIONAL
FORMAT A power consumption threshold has been exceeded.: A power consumption threshold has been exceeded.
SDESC

A power consumption threshold has been exceeded. 
--  Keywords for HP SIM integration
Variables:
  1: sunHwTrapSystemIdentifier
  2: sunHwTrapChassisId
  3: sunHwTrapProductName
  4: sunHwTrapComponentName
  5: sunHwTrapThresholdType
  6: sunHwTrapThresholdValue
  7: sunHwTrapSensorValue
  8: sunHwTrapAdditionalInfo
  9: sunHwTrapAssocObjectId
  10: sunHwTrapSeverity
EDESC
#
#
#
EVENT sunHwTrapPowerConsumptionThresholdDeasserted .1.3.6.1.4.1.42.2.175.103.2.0.73 "Status Events" INFORMATIONAL
FORMAT A power consumption threshold has been deasserted.: A power consumption threshold has been deasserted.
SDESC

A power consumption threshold has been deasserted. 
--  Keywords for HP SIM integration
Variables:
  1: sunHwTrapSystemIdentifier
  2: sunHwTrapChassisId
  3: sunHwTrapProductName
  4: sunHwTrapThresholdType
  5: sunHwTrapThresholdValue
  6: sunHwTrapSensorValue
  7: sunHwTrapAdditionalInfo
  8: sunHwTrapSeverity
EDESC
