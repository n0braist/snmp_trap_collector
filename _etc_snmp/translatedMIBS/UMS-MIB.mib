--
-- Primitive types
--
Boolean  ::= INTEGER (0..1)
Uint8    ::= INTEGER (0..255)
Sint8    ::= INTEGER (-128..127)
Uint16   ::= INTEGER (0..65535)
Sint16   ::= INTEGER (-32767..32766)
-MIB DEFINITIONS ::= BEGIN

IMPORTS
   OBJECT-TYPE
      FROM RFC-1212

   enterprises
      FROM RFC1155-SMI;

ibm                              OBJECT IDENTIFIER ::= { enterprises 2 }
ibmProd                          OBJECT IDENTIFIER ::= { ibm 6 }
umservices                       OBJECT IDENTIFIER ::= { ibmProd 159 }

cimv2                            OBJECT IDENTIFIER ::= { umservices 1 }

--
-- ibmpsg components
--
ibmpsg                           OBJECT IDENTIFIER ::= { cimv2 1 }

ibmpsgEvent                      OBJECT IDENTIFIER ::= { ibmpsg 0 }

ibmpsgAgent                      OBJECT IDENTIFIER ::= { ibmpsg 10 }
ibmpsgEventSubsystem             OBJECT IDENTIFIER ::= { ibmpsg 20 }
ibmpsgHealth                     OBJECT IDENTIFIER ::= { ibmpsg 30 }
ibmpsgVitalProductData           OBJECT IDENTIFIER ::= { ibmpsg 40 }
ibmpsgSMART                      OBJECT IDENTIFIER ::= { ibmpsg 50 }
ibmpsgAssetID                    OBJECT IDENTIFIER ::= { ibmpsg 60 }
ibmpsgAlertOnLAN                 OBJECT IDENTIFIER ::= { ibmpsg 70 }
ibmpsgLMSensor                   OBJECT IDENTIFIER ::= { ibmpsg 80 }
ibmpsgITDirector                 OBJECT IDENTIFIER ::= { ibmpsg 90 }

--
-- win32 components
--
win32                            OBJECT IDENTIFIER ::= { cimv2 2 }

win32Event                       OBJECT IDENTIFIER ::= { win32 0 }

win32WMI                         OBJECT IDENTIFIER ::= { win32 10 }
win32SMBIOS                      OBJECT IDENTIFIER ::= { win32 20 }

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= INTEGER (0..1)
Sint64   ::= INTEGER (-1..1)
Real32   ::= INTEGER (-1..1)
Real64   ::= INTEGER (-1..1)
String   ::= OCTET STRING
Datetime ::= OCTET STRING

END
