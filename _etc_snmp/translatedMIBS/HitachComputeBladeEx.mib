-- Version 00-06
---------------------------------------------------
HitachiComputeBladeEx-MIB DEFINITIONS ::= BEGIN

IMPORTS
    OBJECT-TYPE, MODULE-IDENTITY, NOTIFICATION-TYPE, enterprises, 
    Integer32
        FROM SNMPv2-SMI
    TEXTUAL-CONVENTION, DisplayString
        FROM SNMPv2-TC;

computeBlade MODULE-IDENTITY
    LAST-UPDATED "201306060929Z"
    ORGANIZATION "Hitachi, Ltd."
    CONTACT-INFO 
    ""
    DESCRIPTION 
        "The MIB module to describe HitachiComputeBlade systems."
::= { compute  1 }


hitachi              OBJECT IDENTIFIER ::= { enterprises 116 }

systemExMib     OBJECT IDENTIFIER ::= { hitachi 5 }

compute     OBJECT IDENTIFIER ::= { systemExMib  52 } 

chassis    OBJECT IDENTIFIER ::= { computeBlade 1 } 

chassisBasicInfo    OBJECT IDENTIFIER ::= { chassis 1 } 

chassisInfoType    OBJECT-TYPE
    SYNTAX    INTEGER {
    Rackmount(1),Blade(2),Tower(3)
    }
    MAX-ACCESS    read-only
    STATUS    current
    DESCRIPTION    "This shows the chassis type of server chassis."
    ::= { chassisBasicInfo 1 }

chassisInfoProductName    OBJECT-TYPE
    SYNTAX    DisplayString (SIZE(0..40))
    MAX-ACCESS    read-only
    STATUS    current
    DESCRIPTION    "This shows the product name of server chassis."
    ::= { chassisBasicInfo 2 }

chassisInfoModel    OBJECT-TYPE
    SYNTAX    DisplayString (SIZE(0..40))
    MAX-ACCESS    read-only
    STATUS    current
    DESCRIPTION    "This shows the model name of server chassis."
    ::= { chassisBasicInfo 3 }

chassisInfoSerialNum    OBJECT-TYPE
    SYNTAX    DisplayString (SIZE(0..40))
    MAX-ACCESS    read-only
    STATUS    current
    DESCRIPTION    "This shows the serial number of server chassis."
    ::= { chassisBasicInfo 4 }

chassisInfoChassisID    OBJECT-TYPE
    SYNTAX    DisplayString (SIZE(0..40))
    MAX-ACCESS    read-only
    STATUS    current
    DESCRIPTION    "This shows the chassis ID of server chassis."
    ::= { chassisBasicInfo 5 }

chassisInfoSpec    OBJECT IDENTIFIER ::= { chassisBasicInfo 20 } 

chassisSpecInputCurrentType    OBJECT-TYPE
    SYNTAX    INTEGER {
    ac(1),dc(2),unknown(3)
    }
    MAX-ACCESS    read-only
    STATUS    current
    DESCRIPTION    "This shows the currency type of server chassis."
    ::= { chassisInfoSpec 1 }

chassisSpecRateVoltage    OBJECT-TYPE
    SYNTAX    Integer32
    UNITS    "0.1 V"
    MAX-ACCESS    read-only
    STATUS    current
    DESCRIPTION    "This shows the rated voltage of server chassis."
    ::= { chassisInfoSpec 2 }

chassisSpecTempUpperLimit    OBJECT-TYPE
    SYNTAX    Integer32
    UNITS    "0.1 degrees C"
    MAX-ACCESS    read-only
    STATUS    current
    DESCRIPTION    "This shows the maximum limited temperature of server chassis."
    ::= { chassisInfoSpec 3 }

chassisSpecTempLowerLimit    OBJECT-TYPE
    SYNTAX    Integer32
    UNITS    "0.1 degrees C"
    MAX-ACCESS    read-only
    STATUS    current
    DESCRIPTION    "This shows the minimum limited temperature of server chassis."
    ::= { chassisInfoSpec 4 }

chassisSpecConsumptionCurrent    OBJECT-TYPE
    SYNTAX    Integer32
    UNITS    "0.1 A"
    MAX-ACCESS    read-only
    STATUS    current
    DESCRIPTION    "This shows the consumption current of server chassis.(in current configuration)"
    ::= { chassisInfoSpec 5 }

chassisSpecPowerConsumption    OBJECT-TYPE
    SYNTAX    Integer32
    UNITS    "0.1 kW"
    MAX-ACCESS    read-only
    STATUS    current
    DESCRIPTION    "This shows the power consumption of server chassis.(in current configuration)"
    ::= { chassisInfoSpec 6 }

chassisSpecConsumptionCurrentMaxConfig    OBJECT-TYPE
    SYNTAX    Integer32
    UNITS    "0.1 A"
    MAX-ACCESS    read-only
    STATUS    current
    DESCRIPTION    "This shows the consumption current of server chassis.(in largest configuration)"
    ::= { chassisInfoSpec 7 }

chassisSpecPowerConsumptionMaxConfig    OBJECT-TYPE
    SYNTAX    Integer32
    UNITS    "0.1 kW"
    MAX-ACCESS    read-only
    STATUS    current
    DESCRIPTION    "This shows the power consumption of server chassis.(in largest configuration)"
    ::= { chassisInfoSpec 8 }

chassisSpecMaxAirVolume    OBJECT-TYPE
    SYNTAX    Integer32
    UNITS    "0.1 m^3/min"
    MAX-ACCESS    read-only
    STATUS    current
    DESCRIPTION    "This shows the maximum air volume of server chassis."
    ::= { chassisInfoSpec 9 }

chassisSpecHeight    OBJECT-TYPE
    SYNTAX    Integer32
    UNITS    "U"
    MAX-ACCESS    read-only
    STATUS    current
    DESCRIPTION    "This shows the height of server chassis."
    ::= { chassisInfoSpec 10 }

chassisSpecTotalMass    OBJECT-TYPE
    SYNTAX    Integer32
    UNITS    "0.1 kg"
    MAX-ACCESS    read-only
    STATUS    current
    DESCRIPTION    "This shows the weight of server chassis."
    ::= { chassisInfoSpec 11 }

chassisSpecSize    OBJECT-TYPE
    SYNTAX    DisplayString (SIZE(0..40))
    MAX-ACCESS    read-only
    STATUS    current
    DESCRIPTION    "This shows the size of server chassis."
    ::= { chassisInfoSpec 12 }

chassisCapacity    OBJECT IDENTIFIER ::= { chassis 2 } 

chassisCapacityBladeSlot    OBJECT-TYPE
    SYNTAX    Integer32
    MAX-ACCESS    read-only
    STATUS    current
    DESCRIPTION    "This shows the capacity of server blade slots of server chassis."
    ::= { chassisCapacity 1 }

chassisCapacityMMSlot    OBJECT-TYPE
    SYNTAX    Integer32
    MAX-ACCESS    read-only
    STATUS    current
    DESCRIPTION    "This shows the capacity of management module slots of server chassis."
    ::= { chassisCapacity 2 }

chassisCapacitySWSlot    OBJECT-TYPE
    SYNTAX    Integer32
    MAX-ACCESS    read-only
    STATUS    current
    DESCRIPTION    "This shows the capacity of switch module slots of server chassis."
    ::= { chassisCapacity 3 }

chassisCapacityFanSlot    OBJECT-TYPE
    SYNTAX    Integer32
    MAX-ACCESS    read-only
    STATUS    current
    DESCRIPTION    "This shows the capacity of fan module slots of server chassis."
    ::= { chassisCapacity 4 }

chassisCapacityPowerSupplySlot    OBJECT-TYPE
    SYNTAX    Integer32
    MAX-ACCESS    read-only
    STATUS    current
    DESCRIPTION    "This shows the capacity of power supply module slots of server chassis."
    ::= { chassisCapacity 5 }

chassisCapacityFrontPanelLED    OBJECT-TYPE
    SYNTAX    Integer32
    MAX-ACCESS    read-only
    STATUS    current
    DESCRIPTION    "This shows the capacity of count of LEDs of front panel."
    ::= { chassisCapacity 7 }

chassisState    OBJECT IDENTIFIER ::= { chassis 4 } 

chassisStatePower    OBJECT-TYPE
    SYNTAX    INTEGER {
    Poweroff(1), standby(2), PowerOn(3), unknown(4), Power-on-executing(5), Power-off-executing(6)
    }
    MAX-ACCESS    read-only
    STATUS    current
    DESCRIPTION    "This shows the power supply state of server chassis."
    ::= { chassisState 1 }

chassisStateCurrentVoltage    OBJECT-TYPE
    SYNTAX    Integer32
    UNITS    "0.1 V"
    MAX-ACCESS    read-only
    STATUS    current
    DESCRIPTION    "This shows the current voltage of server chassis."
    ::= { chassisState 2 }

chassisStateConsumptionCurrent    OBJECT-TYPE
    SYNTAX    Integer32
    UNITS    "0.1 A"
    MAX-ACCESS    read-only
    STATUS    current
    DESCRIPTION    "This shows the consumption current of server chassis."
    ::= { chassisState 3 }

chassisStatePowerConsumption    OBJECT-TYPE
    SYNTAX    Integer32
    UNITS    "0.1 kW"
    MAX-ACCESS    read-only
    STATUS    current
    DESCRIPTION    "This shows the power consumption of server chassis."
    ::= { chassisState 4 }

chassisStateIntakeTemp    OBJECT-TYPE
    SYNTAX    INTEGER {
    normal (1), higher-warning (2), higher-error (3), lower-warning (4), unknown(5)
    }
    MAX-ACCESS    read-only
    STATUS    current
    DESCRIPTION    "This shows the state of intake temperature of server chassis."
    ::= { chassisState 5 }

chassisStateFanAirVolume    OBJECT-TYPE
    SYNTAX    Integer32
    UNITS    "0.1 m^3/min"
    MAX-ACCESS    read-only
    STATUS    current
    DESCRIPTION    "This shows the air volume of server chassis."
    ::= { chassisState 6 }

chassisRedundancy    OBJECT IDENTIFIER ::= { chassisState 7 } 

chassisRedundancyMM    OBJECT-TYPE
    SYNTAX    INTEGER {
    redundancy(1), non-redundancy(2),unknown(3)
    }
    MAX-ACCESS    read-only
    STATUS    current
    DESCRIPTION    "This shows the redundancy of management module of server chassis."
    ::= { chassisRedundancy 1 }

chassisRedundancyFan    OBJECT-TYPE
    SYNTAX    INTEGER {
    redundancy(1), non-redundancy(2),unknown(3)
    }
    MAX-ACCESS    read-only
    STATUS    current
    DESCRIPTION    "This shows the redundancy of fan module of server chassis."
    ::= { chassisRedundancy 2 }

chassisRedundancyPowerSupply    OBJECT-TYPE
    SYNTAX    INTEGER {
    redundancy(1), non-redundancy(2),unknown(3)
    }
    MAX-ACCESS    read-only
    STATUS    current
    DESCRIPTION    "This shows the redundancy of power supply module of server chassis."
    ::= { chassisRedundancy 3 }

chassisFrontPanelLEDTable    OBJECT-TYPE
    SYNTAX SEQUENCE OF chassisFrontPanelLEDEntry
    MAX-ACCESS not-accessible
    STATUS     current
    DESCRIPTION "This shows the table of front panel LED of server chassis."
    ::= { chassisState 8 }

chassisFrontPanelLEDEntry    OBJECT-TYPE
    SYNTAX ChassisFrontPanelLEDEntry
    MAX-ACCESS not-accessible
    STATUS    current
    DESCRIPTION "This shows the entry of front panel LED of server chassis."
    INDEX { chassisFrontPanelLEDIndex }
    ::= { chassisFrontPanelLEDTable 1 }

chassisFrontPanelLEDIndex    OBJECT-TYPE
    SYNTAX    Integer32
    MAX-ACCESS    read-only
    STATUS    current
    DESCRIPTION    "This shows the index of front panel LED of server chassis."
    ::= { chassisFrontPanelLEDEntry 1 }

chassisFrontPanelLEDName    OBJECT-TYPE
    SYNTAX    DisplayString (SIZE(0..40))
    MAX-ACCESS    read-only
    STATUS    current
    DESCRIPTION    "This shows the name of front panel LED of server chassis."
    ::= { chassisFrontPanelLEDEntry 2 }

chassisFrontPanelLEDState    OBJECT-TYPE
    SYNTAX    INTEGER {
    turn-off(1), turn-on(2),  unknown(3), blink(4), blink-fast(5), blink-slow(6)
    }
    MAX-ACCESS    read-only
    STATUS    current
    DESCRIPTION    "This shows the state of front panel LED of server chassis."
    ::= { chassisFrontPanelLEDEntry 3 }

chassisFrontPanelLEDColor    OBJECT-TYPE
    SYNTAX    INTEGER {
    blue (1),green (2),red (3),amber (4),unknown (5)
    }
    MAX-ACCESS    read-only
    STATUS    current
    DESCRIPTION    "This shows the color of front panel LED of server chassis."
    ::= { chassisFrontPanelLEDEntry 4 }

chassisStatePowerConsumptionDetail    OBJECT-TYPE
    SYNTAX    Integer32
    UNITS    "W"
    MAX-ACCESS    read-only
    STATUS    current
    DESCRIPTION    "This shows the power consumption of server chassis.(details)"
    ::= { chassisState 9 }

chassisStatePowerConsumptionAverage    OBJECT-TYPE
    SYNTAX    Integer32
    UNITS    "W"
    MAX-ACCESS    read-only
    STATUS    current
    DESCRIPTION    "This shows the power consumption of server chassis.(average)"
    ::= { chassisState 10 }

chassisStateIntakeTempValue    OBJECT-TYPE
    SYNTAX    Integer32
    UNITS    "0.1 degrees C"
    MAX-ACCESS    read-only
    STATUS    current
    DESCRIPTION    "This shows the value of intake temperature of server chassis."
    ::= { chassisState 11 }

ChassisFrontPanelLEDEntry ::= SEQUENCE {
    chassisFrontPanelLEDIndex
        Integer32,
    chassisFrontPanelLEDName
        DisplayString,
    chassisFrontPanelLEDState
        INTEGER,
    chassisFrontPanelLEDColor
        INTEGER,
    chassisStatePowerConsumptionDetail
        Integer32,
    chassisStatePowerConsumptionAverage
        Integer32,
    chassisStateIntakeTempValue
        Integer32
}

chassisStateOther    OBJECT IDENTIFIER ::= { chassisState 20 } 

chassisMaintMode    OBJECT-TYPE
    SYNTAX    INTEGER {
    Normal(1), CE-Maint-mode(2), User-Maint-mode(3), unknown(4)
    }
    MAX-ACCESS    read-only
    STATUS    current
    DESCRIPTION    "This shows the maintenance mode of server chassis."
    ::= { chassisStateOther 1 }

chassisMaintModeFrontPanel    OBJECT-TYPE
    SYNTAX    INTEGER {
    Normal(1), CE-Maint-mode(2), User-Maint-mode(3), unknown(4)
    }
    MAX-ACCESS    read-only
    STATUS    current
    DESCRIPTION    "This shows the maintenance mode of server chassis.(front panel)"
    ::= { chassisStateOther 2 }

chassisLatestHWLogInfo    OBJECT-TYPE
    SYNTAX    DisplayString 
    MAX-ACCESS    read-only
    STATUS    current
    DESCRIPTION    "This shows the information on the newest HW logs of server chassis."
    ::= { chassisState 30 }

chassisHWLogTable    OBJECT-TYPE
    SYNTAX SEQUENCE OF chassisHWLogEntry
    MAX-ACCESS not-accessible
    STATUS     current
    DESCRIPTION "This shows the table on the hardware logs of server chassis."
    ::= { chassisState 31 }

chassisHWLogEntry    OBJECT-TYPE
    SYNTAX ChassisHWLogEntry
    MAX-ACCESS not-accessible
    STATUS    current
    DESCRIPTION "This shows the entry on the hardware logs of server chassis."
    INDEX { chassisHWLogIndex }
    ::= { chassisHWLogTable 1 }

chassisHWLogIndex    OBJECT-TYPE
    SYNTAX    Integer32
    MAX-ACCESS    read-only
    STATUS    current
    DESCRIPTION    "This shows the index on the hardware logs of server chassis."
    ::= { chassisHWLogEntry 1 }

chassisHWLogExist    OBJECT-TYPE
    SYNTAX    INTEGER {
    non-exist(1), exist(2), unknown(3)
    }
    MAX-ACCESS    read-only
    STATUS    current
    DESCRIPTION    "This shows the registrated state on the hardware logs of server chassis."
    ::= { chassisHWLogEntry 2 }

chassisHWLogGenerateID    OBJECT-TYPE
    SYNTAX    DisplayString 
    MAX-ACCESS    read-only
    STATUS    current
    DESCRIPTION    "This shows the occurred part on the hardware logs of server chassis."
    ::= { chassisHWLogEntry 3 }

chassisHWLogRecordID    OBJECT-TYPE
    SYNTAX    DisplayString 
    MAX-ACCESS    read-only
    STATUS    current
    DESCRIPTION    "This shows the recorded ID on the hardware logs of server chassis."
    ::= { chassisHWLogEntry 4 }

chassisHWLogDate    OBJECT-TYPE
    SYNTAX    DisplayString 
    MAX-ACCESS    read-only
    STATUS    current
    DESCRIPTION    "This shows the occurred date and time on the hardware logs of server chassis."
    ::= { chassisHWLogEntry 5 }

chassisHWLogCode    OBJECT-TYPE
    SYNTAX    DisplayString 
    MAX-ACCESS    read-only
    STATUS    current
    DESCRIPTION    "This shows the occurred event code on the hardware logs of server chassis."
    ::= { chassisHWLogEntry 6 }

chassisHWLogDetail    OBJECT-TYPE
    SYNTAX    DisplayString 
    MAX-ACCESS    read-only
    STATUS    current
    DESCRIPTION    "This shows the occurred event detail on the hardware logs of server chassis."
    ::= { chassisHWLogEntry 7 }

ChassisHWLogEntry ::= SEQUENCE {
    chassisHWLogIndex
        Integer32,
    chassisHWLogExist
        INTEGER,
    chassisHWLogGenerateID
        DisplayString,
    chassisHWLogRecordID
        DisplayString,
    chassisHWLogDate
        DisplayString,
    chassisHWLogCode
        DisplayString,
    chassisHWLogDetail
        DisplayString
}

chassisInstall    OBJECT IDENTIFIER ::= { chassisState 40 } 

chassisInsFrontPanelExist    OBJECT-TYPE
    SYNTAX    INTEGER {
    non-exist(1), exist(2), unknown(3)
    }
    MAX-ACCESS    read-only
    STATUS    current
    DESCRIPTION    "This shows the installed state of front panel of server chassis."
    ::= { chassisInstall 1 }

chassisInsBladeSlotTable    OBJECT-TYPE
    SYNTAX SEQUENCE OF chassisInsBladeSlotEntry
    MAX-ACCESS not-accessible
    STATUS     current
    DESCRIPTION "This shows the table of blade slot of server chassis."
    ::= { chassisInstall 2 }

chassisInsBladeSlotEntry    OBJECT-TYPE
    SYNTAX ChassisInsBladeSlotEntry
    MAX-ACCESS not-accessible
    STATUS    current
    DESCRIPTION "This shows the entry of blade slot of server chassis."
    INDEX { chassisInsBladeSlotIndex }
    ::= { chassisInsBladeSlotTable 1 }

chassisInsBladeSlotIndex    OBJECT-TYPE
    SYNTAX    Integer32
    MAX-ACCESS    read-only
    STATUS    current
    DESCRIPTION    "This shows the index of blade slot of server chassis."
    ::= { chassisInsBladeSlotEntry 1 }

chassisInsBladeSlotNum    OBJECT-TYPE
    SYNTAX    Integer32
    MAX-ACCESS    read-only
    STATUS    current
    DESCRIPTION    "This shows the number of blade slots of server chassis."
    ::= { chassisInsBladeSlotEntry 2 }

chassisInsBladeSlotExist    OBJECT-TYPE
    SYNTAX    INTEGER {
    non-exist(1), exist(2), unknown(3)
    }
    MAX-ACCESS    read-only
    STATUS    current
    DESCRIPTION    "This shows the registrated state of blade slot of server chassis."
    ::= { chassisInsBladeSlotEntry 3 }

chassisInsBladeSlotObjectID    OBJECT-TYPE
    SYNTAX    OBJECT IDENTIFIER
    MAX-ACCESS    read-only
    STATUS    current
    DESCRIPTION    "This shows the object ID of blade slot of server chassis."
    ::= { chassisInsBladeSlotEntry 4 }

ChassisInsBladeSlotEntry ::= SEQUENCE {
    chassisInsBladeSlotIndex
        Integer32,
    chassisInsBladeSlotNum
        Integer32,
    chassisInsBladeSlotExist
        INTEGER,
    chassisInsBladeSlotObjectID
        OBJECT IDENTIFIER
}

chassisInsMMSlotTable    OBJECT-TYPE
    SYNTAX SEQUENCE OF chassisInsMMSlotEntry
    MAX-ACCESS not-accessible
    STATUS     current
    DESCRIPTION "This shows the table of management module slot of server chassis."
    ::= { chassisInstall 3 }

chassisInsMMSlotEntry    OBJECT-TYPE
    SYNTAX ChassisInsMMSlotEntry
    MAX-ACCESS not-accessible
    STATUS    current
    DESCRIPTION "This shows the entry of management module slot of server chassis."
    INDEX { chassisInsMMSlotIndex }
    ::= { chassisInsMMSlotTable 1 }

chassisInsMMSlotIndex    OBJECT-TYPE
    SYNTAX    Integer32
    MAX-ACCESS    read-only
    STATUS    current
    DESCRIPTION    "This shows the index of management module slot of server chassis."
    ::= { chassisInsMMSlotEntry 1 }

chassisInsMMSlotNum    OBJECT-TYPE
    SYNTAX    Integer32
    MAX-ACCESS    read-only
    STATUS    current
    DESCRIPTION    "This shows the number of management module slots of server chassis."
    ::= { chassisInsMMSlotEntry 2 }

chassisInsMMSlotExist    OBJECT-TYPE
    SYNTAX    INTEGER {
    non-exist(1), exist(2), unknown(3)
    }
    MAX-ACCESS    read-only
    STATUS    current
    DESCRIPTION    "This shows the registrated state of management module slots of server chassis."
    ::= { chassisInsMMSlotEntry 3 }

chassisInsMMSlotObjectID    OBJECT-TYPE
    SYNTAX    OBJECT IDENTIFIER
    MAX-ACCESS    read-only
    STATUS    current
    DESCRIPTION    "This shows the object ID of management module slot of server chassis."
    ::= { chassisInsMMSlotEntry 4 }

ChassisInsMMSlotEntry ::= SEQUENCE {
    chassisInsMMSlotIndex
        Integer32,
    chassisInsMMSlotNum
        Integer32,
    chassisInsMMSlotExist
        INTEGER,
    chassisInsMMSlotObjectID
        OBJECT IDENTIFIER
}

chassisInsSWSlotTable    OBJECT-TYPE
    SYNTAX SEQUENCE OF chassisInsSWSlotEntry
    MAX-ACCESS not-accessible
    STATUS     current
    DESCRIPTION "This shows the table of switch module slot of server chassis."
    ::= { chassisInstall 4 }

chassisInsSWSlotEntry    OBJECT-TYPE
    SYNTAX ChassisInsSWSlotEntry
    MAX-ACCESS not-accessible
    STATUS    current
    DESCRIPTION "This shows the entry of switch module slot of server chassis."
    INDEX { chassisInsSWSlotIndex }
    ::= { chassisInsSWSlotTable 1 }

chassisInsSWSlotIndex    OBJECT-TYPE
    SYNTAX    Integer32
    MAX-ACCESS    read-only
    STATUS    current
    DESCRIPTION    "This shows the index of switch module slot of server chassis."
    ::= { chassisInsSWSlotEntry 1 }

chassisInsSWSlotNum    OBJECT-TYPE
    SYNTAX    Integer32
    MAX-ACCESS    read-only
    STATUS    current
    DESCRIPTION    "This shows the number of switch module slots of server chassis."
    ::= { chassisInsSWSlotEntry 2 }

chassisInsSWSlotExist    OBJECT-TYPE
    SYNTAX    INTEGER {
    non-exist(1), exist(2), unknown(3)
    }
    MAX-ACCESS    read-only
    STATUS    current
    DESCRIPTION    "This shows the registrated state of switch module slot of server chassis."
    ::= { chassisInsSWSlotEntry 3 }

chassisInsSWSlotObjectID    OBJECT-TYPE
    SYNTAX    OBJECT IDENTIFIER
    MAX-ACCESS    read-only
    STATUS    current
    DESCRIPTION    "This shows the object ID of switch module slot of server chassis."
    ::= { chassisInsSWSlotEntry 4 }

ChassisInsSWSlotEntry ::= SEQUENCE {
    chassisInsSWSlotIndex
        Integer32,
    chassisInsSWSlotNum
        Integer32,
    chassisInsSWSlotExist
        INTEGER,
    chassisInsSWSlotObjectID
        OBJECT IDENTIFIER
}

chassisInsFanSlotTable    OBJECT-TYPE
    SYNTAX SEQUENCE OF chassisInsFanSlotEntry
    MAX-ACCESS not-accessible
    STATUS     current
    DESCRIPTION "This shows the table of fan module slot of server chassis."
    ::= { chassisInstall 5 }

chassisInsFanSlotEntry    OBJECT-TYPE
    SYNTAX ChassisInsFanSlotEntry
    MAX-ACCESS not-accessible
    STATUS    current
    DESCRIPTION "This shows the entry of fan module slot of server chassis."
    INDEX { chassisInsFanSlotIndex }
    ::= { chassisInsFanSlotTable 1 }

chassisInsFanSlotIndex    OBJECT-TYPE
    SYNTAX    Integer32
    MAX-ACCESS    read-only
    STATUS    current
    DESCRIPTION    "This shows the index of fan module slot of server chassis."
    ::= { chassisInsFanSlotEntry 1 }

chassisInsFanSlotNum    OBJECT-TYPE
    SYNTAX    Integer32
    MAX-ACCESS    read-only
    STATUS    current
    DESCRIPTION    "This shows the number of fan module slots of server chassis."
    ::= { chassisInsFanSlotEntry 2 }

chassisInsFanSlotExist    OBJECT-TYPE
    SYNTAX    INTEGER {
    non-exist(1), exist(2), unknown(3)
    }
    MAX-ACCESS    read-only
    STATUS    current
    DESCRIPTION    "This shows the registrated state of fan module slot of server chassis."
    ::= { chassisInsFanSlotEntry 3 }

chassisInsFanSlotObjectID    OBJECT-TYPE
    SYNTAX    OBJECT IDENTIFIER
    MAX-ACCESS    read-only
    STATUS    current
    DESCRIPTION    "This shows the object ID of fan module slot of server chassis."
    ::= { chassisInsFanSlotEntry 4 }

ChassisInsFanSlotEntry ::= SEQUENCE {
    chassisInsFanSlotIndex
        Integer32,
    chassisInsFanSlotNum
        Integer32,
    chassisInsFanSlotExist
        INTEGER,
    chassisInsFanSlotObjectID
        OBJECT IDENTIFIER
}

chassisInsPowerSupplySlotTable    OBJECT-TYPE
    SYNTAX SEQUENCE OF chassisInsPowerSupplySlotEntry
    MAX-ACCESS not-accessible
    STATUS     current
    DESCRIPTION "This shows the table of power supply module slot of server chassis."
    ::= { chassisInstall 6 }

chassisInsPowerSupplySlotEntry    OBJECT-TYPE
    SYNTAX ChassisInsPowerSupplySlotEntry
    MAX-ACCESS not-accessible
    STATUS    current
    DESCRIPTION "This shows the entry of power supply module slot of server chassis."
    INDEX { chassisInsPowerSupplySlotIndex }
    ::= { chassisInsPowerSupplySlotTable 1 }

chassisInsPowerSupplySlotIndex    OBJECT-TYPE
    SYNTAX    Integer32
    MAX-ACCESS    read-only
    STATUS    current
    DESCRIPTION    "This shows the index of power supply module slot of server chassis."
    ::= { chassisInsPowerSupplySlotEntry 1 }

chassisInsPowerSupplySlotNum    OBJECT-TYPE
    SYNTAX    Integer32
    MAX-ACCESS    read-only
    STATUS    current
    DESCRIPTION    "This shows the number of power supply module slots of server chassis."
    ::= { chassisInsPowerSupplySlotEntry 2 }

chassisInsPowerSupplySlotExist    OBJECT-TYPE
    SYNTAX    INTEGER {
    non-exist(1), exist(2), unknown(3)
    }
    MAX-ACCESS    read-only
    STATUS    current
    DESCRIPTION    "This shows the registrated state of power supply module slot of server chassis."
    ::= { chassisInsPowerSupplySlotEntry 3 }

chassisInsPowerSupplySlotObjectID    OBJECT-TYPE
    SYNTAX    OBJECT IDENTIFIER
    MAX-ACCESS    read-only
    STATUS    current
    DESCRIPTION    "This shows the object ID of power supply module slot of server chassis."
    ::= { chassisInsPowerSupplySlotEntry 4 }

ChassisInsPowerSupplySlotEntry ::= SEQUENCE {
    chassisInsPowerSupplySlotIndex
        Integer32,
    chassisInsPowerSupplySlotNum
        Integer32,
    chassisInsPowerSupplySlotExist
        INTEGER,
    chassisInsPowerSupplySlotObjectID
        OBJECT IDENTIFIER
}

chassisFWInfo    OBJECT IDENTIFIER ::= { chassis 5 } 

chassisFWInfoDictionaryVersion    OBJECT-TYPE
    SYNTAX    DisplayString (SIZE(0..40))
    MAX-ACCESS    read-only
    STATUS    current
    DESCRIPTION    "This shows the dictionary version of server chassis."
    ::= { chassisFWInfo 1 }

chassisFWInfoEquipmentParameterVersion    OBJECT-TYPE
    SYNTAX    DisplayString (SIZE(0..40))
    MAX-ACCESS    read-only
    STATUS    current
    DESCRIPTION    "This shows the equipment parameter version of server chassis."
    ::= { chassisFWInfo 2 }

component    OBJECT IDENTIFIER ::= { computeBlade 2 } 

blade    OBJECT IDENTIFIER ::= { component 1 } 

blade1    OBJECT IDENTIFIER ::= { blade 1 } 

blade1BasicInfo    OBJECT IDENTIFIER ::= { blade1 1 } 

blade1InfoProductName    OBJECT-TYPE
    SYNTAX    DisplayString (SIZE(0..40))
    MAX-ACCESS    read-only
    STATUS    current
    DESCRIPTION    "This shows the product name of server blade1."
    ::= { blade1BasicInfo 1 }

blade1InfoModel    OBJECT-TYPE
    SYNTAX    DisplayString (SIZE(0..40))
    MAX-ACCESS    read-only
    STATUS    current
    DESCRIPTION    "This shows the model name of server blade1."
    ::= { blade1BasicInfo 2 }

blade1InfoSerialNum    OBJECT-TYPE
    SYNTAX    DisplayString (SIZE(0..40))
    MAX-ACCESS    read-only
    STATUS    current
    DESCRIPTION    "This shows the serial number of server blade1."
    ::= { blade1BasicInfo 3 }

blade1InfoProductVersion    OBJECT-TYPE
    SYNTAX    DisplayString (SIZE(0..40))
    MAX-ACCESS    read-only
    STATUS    current
    DESCRIPTION    "This shows the product version of server blade1."
    ::= { blade1BasicInfo 4 }

blade1InfoProductManufacturer    OBJECT-TYPE
    SYNTAX    DisplayString (SIZE(0..40))
    MAX-ACCESS    read-only
    STATUS    current
    DESCRIPTION    "This shows the product manufacturer of server blade1."
    ::= { blade1BasicInfo 5 }

blade1InfoBoardProductName    OBJECT-TYPE
    SYNTAX    DisplayString (SIZE(0..40))
    MAX-ACCESS    read-only
    STATUS    current
    DESCRIPTION    "This shows the board product name of server blade1."
    ::= { blade1BasicInfo 7 }

blade1InfoBoardSerialNum    OBJECT-TYPE
    SYNTAX    DisplayString (SIZE(0..40))
    MAX-ACCESS    read-only
    STATUS    current
    DESCRIPTION    "This shows the board serial number of server blade1."
    ::= { blade1BasicInfo 8 }

blade1InfoBoardManufacturer    OBJECT-TYPE
    SYNTAX    DisplayString (SIZE(0..40))
    MAX-ACCESS    read-only
    STATUS    current
    DESCRIPTION    "This shows the board manufacturer of server blade1."
    ::= { blade1BasicInfo 9 }

blade1InfoUUID    OBJECT-TYPE
    SYNTAX    DisplayString (SIZE(0..40))
    MAX-ACCESS    read-only
    STATUS    current
    DESCRIPTION    "This shows UUID(universal Unique ID) of server blade1."
    ::= { blade1BasicInfo 10 }

blade1InfoLogicalPartitionSupport    OBJECT-TYPE
    SYNTAX    INTEGER {
    not-support(1), support(2),unknown(3)
    }
    MAX-ACCESS    read-only
    STATUS    current
    DESCRIPTION    "This shows whether the server blade1 supports HVM or not of server blade1."
    ::= { blade1BasicInfo 11 }

blade1InfoRemoteKVMSupport    OBJECT-TYPE
    SYNTAX    INTEGER {
    not-support(1), support(2),unknown(3)
    }
    MAX-ACCESS    read-only
    STATUS    current
    DESCRIPTION    "This shows whether the server blade1 supports remote KVM or not of server blade1."
    ::= { blade1BasicInfo 12 }

blade1InfoSpec    OBJECT IDENTIFIER ::= { blade1BasicInfo 20 } 

blade1SpecInputCurrentType    OBJECT-TYPE
    SYNTAX    INTEGER {
    ac(1),dc(2),unknown(3)
    }
    MAX-ACCESS    read-only
    STATUS    current
    DESCRIPTION    "This shows the currency type of server blade1."
    ::= { blade1InfoSpec 1 }

blade1SpecRateVoltage    OBJECT-TYPE
    SYNTAX    Integer32
    UNITS    "0.1 V"
    MAX-ACCESS    read-only
    STATUS    current
    DESCRIPTION    "This shows the rated voltage of server blade1."
    ::= { blade1InfoSpec 2 }

blade1SpecConsumptionCurrent    OBJECT-TYPE
    SYNTAX    Integer32
    UNITS    "0.1 A"
    MAX-ACCESS    read-only
    STATUS    current
    DESCRIPTION    "This shows the consumption current of server blade1."
    ::= { blade1InfoSpec 3 }

blade1SpecPowerConsumption    OBJECT-TYPE
    SYNTAX    Integer32
    UNITS    "W"
    MAX-ACCESS    read-only
    STATUS    current
    DESCRIPTION    "This shows the power consumption of server blade1."
    ::= { blade1InfoSpec 4 }

blade1SpecMass    OBJECT-TYPE
    SYNTAX    Integer32
    UNITS    "0.1 kg"
    MAX-ACCESS    read-only
    STATUS    current
    DESCRIPTION    "This shows the weight of server blade1."
    ::= { blade1InfoSpec 5 }

blade1InfoUpperLimitIntakeTemp    OBJECT-TYPE
    SYNTAX    Integer32
    UNITS    "0.1 degrees C"
    MAX-ACCESS    read-only
    STATUS    current
    DESCRIPTION    "This shows the maximum limited intake temperature of server blade1."
    ::= { blade1InfoSpec 6 }

blade1InfoLowerLimitIntakeTemp    OBJECT-TYPE
    SYNTAX    Integer32
    UNITS    "0.1 degrees C"
    MAX-ACCESS    read-only
    STATUS    current
    DESCRIPTION    "This shows the minimum limited intake temperature of server blade1."
    ::= { blade1InfoSpec 7 }

blade1SpecSize    OBJECT-TYPE
    SYNTAX    DisplayString (SIZE(0..40))
    MAX-ACCESS    read-only
    STATUS    current
    DESCRIPTION    "This shows the size of server blade1."
    ::= { blade1InfoSpec 8 }

blade1SpecOccupySlots    OBJECT-TYPE
    SYNTAX    Integer32
    MAX-ACCESS    read-only
    STATUS    current
    DESCRIPTION    "This shows the dedicated number of slots of server blade1."
    ::= { blade1InfoSpec 9 }

blade1SpecExpansionBladeSlot    OBJECT-TYPE
    SYNTAX    Integer32
    MAX-ACCESS    read-only
    STATUS    current
    DESCRIPTION    "This shows the number of slots of expansion blade of server blade1."
    ::= { blade1InfoSpec 10 }

blade1InfoExpansionBladeTable    OBJECT-TYPE
    SYNTAX SEQUENCE OF blade1InfoExpansionBladeEntry
    MAX-ACCESS not-accessible
    STATUS     current
    DESCRIPTION "This shows the table of expansion blade slot of server blade1."
    ::= { blade1BasicInfo 30 }

blade1InfoExpansionBladeEntry    OBJECT-TYPE
    SYNTAX Blade1InfoExpansionBladeEntry
    MAX-ACCESS not-accessible
    STATUS    current
    DESCRIPTION "This shows the entry of expansion blade slot of server blade1."
    INDEX { blade1InfoExpansionBladeIndex }
    ::= { blade1InfoExpansionBladeTable 1 }

blade1InfoExpansionBladeIndex    OBJECT-TYPE
    SYNTAX    Integer32
    MAX-ACCESS    read-only
    STATUS    current
    DESCRIPTION    "This shows the index of expansion blade slot of server blade1."
    ::= { blade1InfoExpansionBladeEntry 1 }

blade1InfoExpansionBladeExist    OBJECT-TYPE
    SYNTAX    INTEGER {
    non-exist(1), exist(2), unknown(3)
    }
    MAX-ACCESS    read-only
    STATUS    current
    DESCRIPTION    "This shows the registrated state of expansion blade of server blade1."
    ::= { blade1InfoExpansionBladeEntry 2 }

blade1InfoExpansionBladeProductName    OBJECT-TYPE
    SYNTAX    DisplayString (SIZE(0..40))
    MAX-ACCESS    read-only
    STATUS    current
    DESCRIPTION    "This shows the product name of expansion blade of server blade1."
    ::= { blade1InfoExpansionBladeEntry 3 }

blade1InfoExpansionBladeModel    OBJECT-TYPE
    SYNTAX    DisplayString (SIZE(0..40))
    MAX-ACCESS    read-only
    STATUS    current
    DESCRIPTION    "This shows the model name of expansion blade of server blade1."
    ::= { blade1InfoExpansionBladeEntry 4 }

blade1InfoExpansionBladeSerialNum    OBJECT-TYPE
    SYNTAX    DisplayString (SIZE(0..40))
    MAX-ACCESS    read-only
    STATUS    current
    DESCRIPTION    "This shows the serial number of expansion blade of server blade1."
    ::= { blade1InfoExpansionBladeEntry 5 }

blade1InfoExpansionBladeProductVersion    OBJECT-TYPE
    SYNTAX    DisplayString (SIZE(0..40))
    MAX-ACCESS    read-only
    STATUS    current
    DESCRIPTION    "This shows the product version of expansion blade of server blade1."
    ::= { blade1InfoExpansionBladeEntry 6 }

blade1InfoExpansionBladeProductManufacturer    OBJECT-TYPE
    SYNTAX    DisplayString (SIZE(0..40))
    MAX-ACCESS    read-only
    STATUS    current
    DESCRIPTION    "This shows the product manufacturer of expansion blade of server blade1."
    ::= { blade1InfoExpansionBladeEntry 7 }

blade1InfoExpansionBladeBoardProductName    OBJECT-TYPE
    SYNTAX    DisplayString (SIZE(0..40))
    MAX-ACCESS    read-only
    STATUS    current
    DESCRIPTION    "This shows the board product name of expansion blade of server blade1."
    ::= { blade1InfoExpansionBladeEntry 9 }

blade1InfoExpansionBladeBoardSerialNum    OBJECT-TYPE
    SYNTAX    DisplayString (SIZE(0..40))
    MAX-ACCESS    read-only
    STATUS    current
    DESCRIPTION    "This shows the board serial number of expansion blade of server blade1."
    ::= { blade1InfoExpansionBladeEntry 10 }

blade1InfoExpansionBladeBoardManufacturer    OBJECT-TYPE
    SYNTAX    DisplayString (SIZE(0..40))
    MAX-ACCESS    read-only
    STATUS    current
    DESCRIPTION    "This shows the board manufacturer of expansion blade of server blade1."
    ::= { blade1InfoExpansionBladeEntry 11 }

Blade1InfoExpansionBladeEntry ::= SEQUENCE {
    blade1InfoExpansionBladeIndex
        Integer32,
    blade1InfoExpansionBladeExist
        INTEGER,
    blade1InfoExpansionBladeProductName
        DisplayString,
    blade1InfoExpansionBladeModel
        DisplayString,
    blade1InfoExpansionBladeSerialNum
        DisplayString,
    blade1InfoExpansionBladeProductVersion
        DisplayString,
    blade1InfoExpansionBladeProductManufacturer
        DisplayString,
    blade1InfoExpansionBladeBoardProductName
        DisplayString,
    blade1InfoExpansionBladeBoardSerialNum
        DisplayString,
    blade1InfoExpansionBladeBoardManufacturer
        DisplayString
}

blade1Capacity    OBJECT IDENTIFIER ::= { blade1 2 } 

blade1CapacityCPUSocket    OBJECT-TYPE
    SYNTAX    Integer32
    MAX-ACCESS    read-only
    STATUS    current
    DESCRIPTION    "This shows the capacity of CPU sockets of server blade1."
    ::= { blade1Capacity 1 }

blade1CapacityDIMMSlot    OBJECT-TYPE
    SYNTAX    Integer32
    MAX-ACCESS    read-only
    STATUS    current
    DESCRIPTION    "This shows the capacity of DIMM slots of server blade1."
    ::= { blade1Capacity 2 }

blade1CapacityPCISlot    OBJECT-TYPE
    SYNTAX    Integer32
    MAX-ACCESS    read-only
    STATUS    current
    DESCRIPTION    "This shows the capacity of PCI slots of server blade1."
    ::= { blade1Capacity 3 }

blade1CapacityLOM    OBJECT-TYPE
    SYNTAX    Integer32
    MAX-ACCESS    read-only
    STATUS    current
    DESCRIPTION    "This shows the capacity of onboard LAN ports of server blade1."
    ::= { blade1Capacity 4 }

blade1CapacityFan    OBJECT-TYPE
    SYNTAX    Integer32
    MAX-ACCESS    read-only
    STATUS    current
    DESCRIPTION    "This shows the capacity of onboard fans of server blade1."
    ::= { blade1Capacity 5 }

blade1CapacityHDDSlot    OBJECT-TYPE
    SYNTAX    Integer32
    MAX-ACCESS    read-only
    STATUS    current
    DESCRIPTION    "This shows the capacity of HDD slots of server blade1."
    ::= { blade1Capacity 6 }

blade1CapacityVoltageSensor    OBJECT-TYPE
    SYNTAX    Integer32
    MAX-ACCESS    read-only
    STATUS    current
    DESCRIPTION    "This shows the capacity of voltage sensors of blade1."
    ::= { blade1Capacity 7 }

blade1CapacityTempSensor    OBJECT-TYPE
    SYNTAX    Integer32
    MAX-ACCESS    read-only
    STATUS    current
    DESCRIPTION    "This shows the capacity of temperature sensors of blade1."
    ::= { blade1Capacity 8 }

blade1CapacityExpansionHDDSlot    OBJECT-TYPE
    SYNTAX    Integer32
    MAX-ACCESS    read-only
    STATUS    current
    DESCRIPTION    "This shows the capacity of expansion HDD slots of server blade1."
    ::= { blade1Capacity 9 }

blade1CapacityLED    OBJECT-TYPE
    SYNTAX    Integer32
    MAX-ACCESS    read-only
    STATUS    current
    DESCRIPTION    "This shows the capacity of count of LEDs of server blade1."
    ::= { blade1Capacity 10 }

blade1Settings    OBJECT IDENTIFIER ::= { blade1 3 } 

blade1SettingsBelongPartitionNum    OBJECT-TYPE
    SYNTAX    Integer32
    MAX-ACCESS    read-only
    STATUS    current
    DESCRIPTION    "This shows the partition number of server blade1."
    ::= { blade1Settings 1 }

blade1SettingsDetailHVMLicenceModel    OBJECT-TYPE
    SYNTAX    DisplayString (SIZE(0..40))
    MAX-ACCESS    read-only
    STATUS    current
    DESCRIPTION    "This shows the HVM licence of detailed server blade1 (model). "
    ::= { blade1Settings 2 }

blade1SettingsDetailHVMLicenceAvailableVersion    OBJECT-TYPE
    SYNTAX    DisplayString (SIZE(0..40))
    MAX-ACCESS    read-only
    STATUS    current
    DESCRIPTION    "This shows the HVM licence of detailed server blade1 (available version). "
    ::= { blade1Settings 3 }

blade1SettingsManagementPortIPAddress    OBJECT-TYPE
    SYNTAX    DisplayString (SIZE(0..40))
    MAX-ACCESS    read-only
    STATUS    current
    DESCRIPTION    "This shows the IP address of management port of server blade1."
    ::= { blade1Settings 4 }

blade1State    OBJECT IDENTIFIER ::= { blade1 4 } 

blade1StateSlotNum    OBJECT-TYPE
    SYNTAX    Integer32
    MAX-ACCESS    read-only
    STATUS    current
    DESCRIPTION    "This shows the number of installed slots of server blade1."
    ::= { blade1State 1 }

blade1StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade1."
    ::= { blade1State 2 }

blade1StateHealth    OBJECT-TYPE
    SYNTAX    INTEGER {
    normal (1),fail (2),unknown (3)
    }
    MAX-ACCESS    read-only
    STATUS    current
    DESCRIPTION    "This shows the health state of server blade1."
    ::= { blade1State 3 }

blade1StatePrimaly    OBJECT-TYPE
    SYNTAX    INTEGER {
    primary(1), non-primary(2),unknown(3)
    }
    MAX-ACCESS    read-only
    STATUS    current
    DESCRIPTION    "This shows the primary state of server blade1."
    ::= { blade1State 4 }

blade1StateCurrentVoltage    OBJECT-TYPE
    SYNTAX    Integer32
    UNITS    "0.1 V"
    MAX-ACCESS    read-only
    STATUS    current
    DESCRIPTION    "This shows the current voltage of server blade1."
    ::= { blade1State 5 }

blade1StateConsumptionCurrent    OBJECT-TYPE
    SYNTAX    Integer32
    UNITS    "0.1 A"
    MAX-ACCESS    read-only
    STATUS    current
    DESCRIPTION    "This shows the consumption current of server blade1."
    ::= { blade1State 6 }

blade1StatePowerConsumption    OBJECT-TYPE
    SYNTAX    Integer32
    UNITS    "W"
    MAX-ACCESS    read-only
    STATUS    current
    DESCRIPTION    "This shows the power consumption of server blade1."
    ::= { blade1State 7 }

blade1StateIntakeTemp    OBJECT-TYPE
    SYNTAX    INTEGER {
    normal (1), higher-warning (2), higher-error (3), lower-warning (4), unknown(5)
    }
    MAX-ACCESS    read-only
    STATUS    current
    DESCRIPTION    "This shows the state of intake temperature of server blade1."
    ::= { blade1State 8 }

blade1StateLEDTable    OBJECT-TYPE
    SYNTAX SEQUENCE OF blade1StateLEDEntry
    MAX-ACCESS not-accessible
    STATUS     current
    DESCRIPTION "This shows the table of LED of server blade1."
    ::= { blade1State 9 }

blade1StateLEDEntry    OBJECT-TYPE
    SYNTAX Blade1StateLEDEntry
    MAX-ACCESS not-accessible
    STATUS    current
    DESCRIPTION "This shows the entry of LED of server blade1."
    INDEX { blade1StateLEDIndex }
    ::= { blade1StateLEDTable 1 }

blade1StateLEDIndex    OBJECT-TYPE
    SYNTAX    Integer32
    MAX-ACCESS    read-only
    STATUS    current
    DESCRIPTION    "This shows the index of LED of server blade1."
    ::= { blade1StateLEDEntry 1 }

blade1StateLEDName    OBJECT-TYPE
    SYNTAX    DisplayString (SIZE(0..40))
    MAX-ACCESS    read-only
    STATUS    current
    DESCRIPTION    "This shows the name of LED of server blade1."
    ::= { blade1StateLEDEntry 2 }

blade1StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade1."
    ::= { blade1StateLEDEntry 3 }

blade1StateLEDColor    OBJECT-TYPE
    SYNTAX    INTEGER {
    blue (1),green (2),red (3),amber (4),unknown (5)
    }
    MAX-ACCESS    read-only
    STATUS    current
    DESCRIPTION    "This shows the color of LED of server blade1."
    ::= { blade1StateLEDEntry 4 }

Blade1StateLEDEntry ::= SEQUENCE {
    blade1StateLEDIndex
        Integer32,
    blade1StateLEDName
        DisplayString,
    blade1StateLEDState
        INTEGER,
    blade1StateLEDColor
        INTEGER
}

blade1StateOther    OBJECT IDENTIFIER ::= { blade1State 20 } 

blade1MaintMode    OBJECT-TYPE
    SYNTAX    INTEGER {
    Normal(1), CE-Maint-mode(2), User-Maint-mode(3), unknown(4)
    }
    MAX-ACCESS    read-only
    STATUS    current
    DESCRIPTION    "This shows the maintenance mode of server blade1."
    ::= { blade1StateOther 1 }

blade1Install    OBJECT IDENTIFIER ::= { blade1State 30 } 

blade1InsCPUSocketTable    OBJECT-TYPE
    SYNTAX SEQUENCE OF blade1InsCPUSocketEntry
    MAX-ACCESS not-accessible
    STATUS     current
    DESCRIPTION "This shows the table of CPU socket of server blade1."
    ::= { blade1Install 1 }

blade1InsCPUSocketEntry    OBJECT-TYPE
    SYNTAX Blade1InsCPUSocketEntry
    MAX-ACCESS not-accessible
    STATUS    current
    DESCRIPTION "This shows the entry of CPU socket of server blade1."
    INDEX { blade1InsCPUSocketIndex }
    ::= { blade1InsCPUSocketTable 1 }

blade1InsCPUSocketIndex    OBJECT-TYPE
    SYNTAX    Integer32
    MAX-ACCESS    read-only
    STATUS    current
    DESCRIPTION    "This shows the index of CPU socket of server blade1."
    ::= { blade1InsCPUSocketEntry 1 }

blade1InsCPUSocketNum    OBJECT-TYPE
    SYNTAX    Integer32
    MAX-ACCESS    read-only
    STATUS    current
    DESCRIPTION    "This shows the number of CPU sockets of server blade1."
    ::= { blade1InsCPUSocketEntry 2 }

blade1InsCPUSocketExist    OBJECT-TYPE
    SYNTAX    INTEGER {
    non-exist(1), exist(2), unknown(3)
    }
    MAX-ACCESS    read-only
    STATUS    current
    DESCRIPTION    "This shows the registrated state of CPU socket of server blade1."
    ::= { blade1InsCPUSocketEntry 3 }

blade1InsCPUSocketCPUName    OBJECT-TYPE
    SYNTAX    DisplayString (SIZE(0..40))
    MAX-ACCESS    read-only
    STATUS    current
    DESCRIPTION    "This shows the CPU name of CPU socket of server blade1."
    ::= { blade1InsCPUSocketEntry 4 }

blade1InsCPUSocketCPUFrequency    OBJECT-TYPE
    SYNTAX    Integer32
    UNITS    "MHz"
    MAX-ACCESS    read-only
    STATUS    current
    DESCRIPTION    "This shows the CPU frequency of CPU socket of server blade1."
    ::= { blade1InsCPUSocketEntry 5 }

blade1InsCPUSocketCPUStepping    OBJECT-TYPE
    SYNTAX    DisplayString 
    MAX-ACCESS    read-only
    STATUS    current
    DESCRIPTION    "This shows the CPU stepping of CPU socket of server blade1."
    ::= { blade1InsCPUSocketEntry 6 }

blade1InsCPUSocketCPUCoreNum    OBJECT-TYPE
    SYNTAX    Integer32
    MAX-ACCESS    read-only
    STATUS    current
    DESCRIPTION    "This shows the CPU core number of CPU socket of server blade1."
    ::= { blade1InsCPUSocketEntry 7 }

blade1InsCPUSocketCPUUpperLimitTemp    OBJECT-TYPE
    SYNTAX    Integer32
    UNITS    "0.1 degrees C"
    MAX-ACCESS    read-only
    STATUS    current
    DESCRIPTION    "This shows the maximum limited CPU temperature of server blade1."
    ::= { blade1InsCPUSocketEntry 8 }

blade1InsCPUSocketCPULowerLimitTemp    OBJECT-TYPE
    SYNTAX    Integer32
    UNITS    "0.1 degrees C"
    MAX-ACCESS    read-only
    STATUS    current
    DESCRIPTION    "This shows the minimum limited CPU temperature of server blade1."
    ::= { blade1InsCPUSocketEntry 9 }

blade1InsDIMMCapacity    OBJECT-TYPE
    SYNTAX    Integer32
    UNITS    "GB"
    MAX-ACCESS    read-only
    STATUS    current
    DESCRIPTION    "This shows the total amount of DIMM capacity of server blade1."
    ::= { blade1Install 2 }

Blade1InsCPUSocketEntry ::= SEQUENCE {
    blade1InsCPUSocketIndex
        Integer32,
    blade1InsCPUSocketNum
        Integer32,
    blade1InsCPUSocketExist
        INTEGER,
    blade1InsCPUSocketCPUName
        DisplayString,
    blade1InsCPUSocketCPUFrequency
        Integer32,
    blade1InsCPUSocketCPUStepping
        DisplayString,
    blade1InsCPUSocketCPUCoreNum
        Integer32,
    blade1InsCPUSocketCPUUpperLimitTemp
        Integer32,
    blade1InsCPUSocketCPULowerLimitTemp
        Integer32,
    blade1InsDIMMCapacity
        Integer32
}

blade1InsDIMMSlotTable    OBJECT-TYPE
    SYNTAX SEQUENCE OF blade1InsDIMMSlotEntry
    MAX-ACCESS not-accessible
    STATUS     current
    DESCRIPTION "This shows the table of DIMM slot of server blade1."
    ::= { blade1Install 3 }

blade1InsDIMMSlotEntry    OBJECT-TYPE
    SYNTAX Blade1InsDIMMSlotEntry
    MAX-ACCESS not-accessible
    STATUS    current
    DESCRIPTION "This shows the entry of DIMM slot of server blade1."
    INDEX { blade1InsDIMMSlotIndex }
    ::= { blade1InsDIMMSlotTable 1 }

blade1InsDIMMSlotIndex    OBJECT-TYPE
    SYNTAX    Integer32
    MAX-ACCESS    read-only
    STATUS    current
    DESCRIPTION    "This shows the index of DIMM slot of server blade1."
    ::= { blade1InsDIMMSlotEntry 1 }

blade1InsDIMMSlotExist    OBJECT-TYPE
    SYNTAX    INTEGER {
    non-exist(1), exist(2), unknown(3)
    }
    MAX-ACCESS    read-only
    STATUS    current
    DESCRIPTION    "This shows the registrated state of DIMM slot of server blade1."
    ::= { blade1InsDIMMSlotEntry 2 }

blade1InsDIMMSlotDIMMCapacity    OBJECT-TYPE
    SYNTAX    Integer32
    UNITS    "GB"
    MAX-ACCESS    read-only
    STATUS    current
    DESCRIPTION    "This shows the capacity of DIMM slots of server blade1."
    ::= { blade1InsDIMMSlotEntry 3 }

blade1InsDIMMSlotDIMMType    OBJECT-TYPE
    SYNTAX    DisplayString 
    MAX-ACCESS    read-only
    STATUS    current
    DESCRIPTION    "This shows the DIMM type of DIMM slot of server blade1."
    ::= { blade1InsDIMMSlotEntry 4 }

blade1InsDIMMSlotDIMMFrequency    OBJECT-TYPE
    SYNTAX    Integer32
    UNITS    "MHz"
    MAX-ACCESS    read-only
    STATUS    current
    DESCRIPTION    "This shows the DIMM frequency of DIMM slot of server blade1."
    ::= { blade1InsDIMMSlotEntry 5 }

blade1InsDIMMSlotDIMMCasLatency    OBJECT-TYPE
    SYNTAX    Integer32
    MAX-ACCESS    read-only
    STATUS    current
    DESCRIPTION    "This shows the DIMM cas latency of DIMM slot of server blade1."
    ::= { blade1InsDIMMSlotEntry 6 }

blade1InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade1."
    ::= { blade1InsDIMMSlotEntry 7 }

Blade1InsDIMMSlotEntry ::= SEQUENCE {
    blade1InsDIMMSlotIndex
        Integer32,
    blade1InsDIMMSlotExist
        INTEGER,
    blade1InsDIMMSlotDIMMCapacity
        Integer32,
    blade1InsDIMMSlotDIMMType
        DisplayString,
    blade1InsDIMMSlotDIMMFrequency
        Integer32,
    blade1InsDIMMSlotDIMMCasLatency
        Integer32,
    blade1InsDIMMSlotDIMMStatus
        INTEGER
}

blade1InsPCISlotTable    OBJECT-TYPE
    SYNTAX SEQUENCE OF blade1InsPCISlotEntry
    MAX-ACCESS not-accessible
    STATUS     current
    DESCRIPTION "This shows the table of PCI slot of server blade1."
    ::= { blade1Install 4 }

blade1InsPCISlotEntry    OBJECT-TYPE
    SYNTAX Blade1InsPCISlotEntry
    MAX-ACCESS not-accessible
    STATUS    current
    DESCRIPTION "This shows the entry of PCI slot of server blade1."
    INDEX { blade1InsPCISlotIndex }
    ::= { blade1InsPCISlotTable 1 }

blade1InsPCISlotIndex    OBJECT-TYPE
    SYNTAX    Integer32
    MAX-ACCESS    read-only
    STATUS    current
    DESCRIPTION    "This shows the index of PCI slot of server blade1."
    ::= { blade1InsPCISlotEntry 1 }

blade1InsPCISlotType    OBJECT-TYPE
    SYNTAX    DisplayString 
    MAX-ACCESS    read-only
    STATUS    current
    DESCRIPTION    "This shows the type of PCI slot of server blade1."
    ::= { blade1InsPCISlotEntry 2 }

blade1InsPCISlotExist    OBJECT-TYPE
    SYNTAX    INTEGER {
    non-exist(1), exist(2), unknown(3)
    }
    MAX-ACCESS    read-only
    STATUS    current
    DESCRIPTION    "This shows the registrated state of PCI slot of server blade1."
    ::= { blade1InsPCISlotEntry 3 }

blade1InsPCISlotPCIType    OBJECT-TYPE
    SYNTAX    DisplayString 
    MAX-ACCESS    read-only
    STATUS    current
    DESCRIPTION    "This shows the PCI type of PCI slot of server blade1."
    ::= { blade1InsPCISlotEntry 4 }

blade1InsPCISlotPCIProductName    OBJECT-TYPE
    SYNTAX    DisplayString 
    MAX-ACCESS    read-only
    STATUS    current
    DESCRIPTION    "This shows the PCI product name of PCI slot of server blade1."
    ::= { blade1InsPCISlotEntry 5 }

blade1InsPCISlotPCISerial    OBJECT-TYPE
    SYNTAX    DisplayString 
    MAX-ACCESS    read-only
    STATUS    current
    DESCRIPTION    "This shows the serial number of PCI slot of server blade1."
    ::= { blade1InsPCISlotEntry 6 }

blade1InsPCISlotPCIManufacturer    OBJECT-TYPE
    SYNTAX    DisplayString 
    MAX-ACCESS    read-only
    STATUS    current
    DESCRIPTION    "This shows the manufacturer of PCI slot of server blade1."
    ::= { blade1InsPCISlotEntry 7 }

blade1InsPCISlotNum    OBJECT-TYPE
    SYNTAX    Integer32
    MAX-ACCESS    read-only
    STATUS    current
    DESCRIPTION    "This shows the number of PCI slots of server blade1."
    ::= { blade1InsPCISlotEntry 8 }

Blade1InsPCISlotEntry ::= SEQUENCE {
    blade1InsPCISlotIndex
        Integer32,
    blade1InsPCISlotType
        DisplayString,
    blade1InsPCISlotExist
        INTEGER,
    blade1InsPCISlotPCIType
        DisplayString,
    blade1InsPCISlotPCIProductName
        DisplayString,
    blade1InsPCISlotPCISerial
        DisplayString,
    blade1InsPCISlotPCIManufacturer
        DisplayString,
    blade1InsPCISlotNum
        Integer32
}

blade1InsLOMTable    OBJECT-TYPE
    SYNTAX SEQUENCE OF blade1InsLOMEntry
    MAX-ACCESS not-accessible
    STATUS     current
    DESCRIPTION "This shows the table of onboard LAN of server blade1."
    ::= { blade1Install 5 }

blade1InsLOMEntry    OBJECT-TYPE
    SYNTAX Blade1InsLOMEntry
    MAX-ACCESS not-accessible
    STATUS    current
    DESCRIPTION "This shows the entry of onboard LAN of server blade1."
    INDEX { blade1InsLOMIndex }
    ::= { blade1InsLOMTable 1 }

blade1InsLOMIndex    OBJECT-TYPE
    SYNTAX    Integer32
    MAX-ACCESS    read-only
    STATUS    current
    DESCRIPTION    "This shows the index of onboard LAN of server blade1."
    ::= { blade1InsLOMEntry 1 }

blade1InsLOMType    OBJECT-TYPE
    SYNTAX    DisplayString 
    MAX-ACCESS    read-only
    STATUS    current
    DESCRIPTION    "This shows the type of onboard LAN of server blade1."
    ::= { blade1InsLOMEntry 2 }

blade1InsLOMLinkSpeed    OBJECT-TYPE
    SYNTAX    Integer32
    UNITS    "bps"
    MAX-ACCESS    read-only
    STATUS    current
    DESCRIPTION    "This shows the link speed of onboard LAN of server blade1."
    ::= { blade1InsLOMEntry 3 }

blade1InsLOMMAC    OBJECT-TYPE
    SYNTAX    DisplayString 
    MAX-ACCESS    read-only
    STATUS    current
    DESCRIPTION    "This shows the MAC address of onboard LAN of server blade1."
    ::= { blade1InsLOMEntry 4 }

blade1InsLOMLinkStatus    OBJECT-TYPE
    SYNTAX    INTEGER {
    up (1),down (2),unknown (3)
    }
    MAX-ACCESS    read-only
    STATUS    current
    DESCRIPTION    "This shows the link state of onboard LAN of server blade1."
    ::= { blade1InsLOMEntry 5 }

blade1InsLOMPortDivide    OBJECT-TYPE
    SYNTAX    INTEGER {
    possible (1),Impossible (2),unknown (3)
    }
    MAX-ACCESS    read-only
    STATUS    current
    DESCRIPTION    "This shows the port divide propriety of onboard LAN of server blade1."
    ::= { blade1InsLOMEntry 6 }

blade1InsLOMPortDivideNum    OBJECT-TYPE
    SYNTAX    Integer32
    MAX-ACCESS    read-only
    STATUS    current
    DESCRIPTION    "This shows the port divide number of onboard LAN of server blade1."
    ::= { blade1InsLOMEntry 7 }

Blade1InsLOMEntry ::= SEQUENCE {
    blade1InsLOMIndex
        Integer32,
    blade1InsLOMType
        DisplayString,
    blade1InsLOMLinkSpeed
        Integer32,
    blade1InsLOMMAC
        DisplayString,
    blade1InsLOMLinkStatus
        INTEGER,
    blade1InsLOMPortDivide
        INTEGER,
    blade1InsLOMPortDivideNum
        Integer32
}

blade1HDDSlotTable    OBJECT-TYPE
    SYNTAX SEQUENCE OF blade1HDDSlotEntry
    MAX-ACCESS not-accessible
    STATUS     current
    DESCRIPTION "This shows the table of HDD slot of server blade1."
    ::= { blade1Install 7 }

blade1HDDSlotEntry    OBJECT-TYPE
    SYNTAX Blade1HDDSlotEntry
    MAX-ACCESS not-accessible
    STATUS    current
    DESCRIPTION "This shows the entry of HDD slot of server blade1."
    INDEX { blade1HDDSlotIndex }
    ::= { blade1HDDSlotTable 1 }

blade1HDDSlotIndex    OBJECT-TYPE
    SYNTAX    Integer32
    MAX-ACCESS    read-only
    STATUS    current
    DESCRIPTION    "This shows the index of HDD slot of server blade1."
    ::= { blade1HDDSlotEntry 1 }

blade1HDDSlotNum    OBJECT-TYPE
    SYNTAX    Integer32
    MAX-ACCESS    read-only
    STATUS    current
    DESCRIPTION    "This shows the number of HDD slots of server blade1."
    ::= { blade1HDDSlotEntry 2 }

blade1HDDSlotExist    OBJECT-TYPE
    SYNTAX    INTEGER {
    non-exist(1), exist(2), unknown(3)
    }
    MAX-ACCESS    read-only
    STATUS    current
    DESCRIPTION    "This shows the registrated state of HDD slot of server blade1."
    ::= { blade1HDDSlotEntry 3 }

blade1HDDSlotHDDType    OBJECT-TYPE
    SYNTAX    DisplayString 
    MAX-ACCESS    read-only
    STATUS    current
    DESCRIPTION    "This shows the HDD type of HDD slot of server blade1."
    ::= { blade1HDDSlotEntry 4 }

blade1HDDSlotHDDProductName    OBJECT-TYPE
    SYNTAX    DisplayString 
    MAX-ACCESS    read-only
    STATUS    current
    DESCRIPTION    "This shows the HDD product name of HDD slot of server blade1."
    ::= { blade1HDDSlotEntry 5 }

blade1HDDSlotHDDModel    OBJECT-TYPE
    SYNTAX    DisplayString 
    MAX-ACCESS    read-only
    STATUS    current
    DESCRIPTION    "This shows the HDD model of HDD slot of server blade1."
    ::= { blade1HDDSlotEntry 6 }

blade1HDDSlotHDDSerialNum    OBJECT-TYPE
    SYNTAX    DisplayString 
    MAX-ACCESS    read-only
    STATUS    current
    DESCRIPTION    "This shows the HDD serial number of HDD slot of server blade1."
    ::= { blade1HDDSlotEntry 7 }

blade1HDDSlotHDDCapacity    OBJECT-TYPE
    SYNTAX    Integer32
    UNITS    "GB"
    MAX-ACCESS    read-only
    STATUS    current
    DESCRIPTION    "This shows the HDD capacity of HDD slots of server blade1."
    ::= { blade1HDDSlotEntry 8 }

blade1HDDSlotHDDRPM    OBJECT-TYPE
    SYNTAX    Integer32
    UNITS    "rpm"
    MAX-ACCESS    read-only
    STATUS    current
    DESCRIPTION    "This shows the HDD drive speed of HDD slot of server blade1."
    ::= { blade1HDDSlotEntry 9 }

blade1HDDSlotHDDStatePower    OBJECT-TYPE
    SYNTAX    INTEGER {
    poweroff (1), poweron (2), unknown (3)
    }
    MAX-ACCESS    read-only
    STATUS    current
    DESCRIPTION    "This shows the HDD power supply state of HDD slot of server blade1."
    ::= { blade1HDDSlotEntry 10 }

blade1HDDSlotHDDStateHealth    OBJECT-TYPE
    SYNTAX    INTEGER {
    normal (1),fail (2),unknown (3),rebuild (4)
    }
    MAX-ACCESS    read-only
    STATUS    current
    DESCRIPTION    "This shows the HDD health state of HDD slot of server blade1."
    ::= { blade1HDDSlotEntry 11 }

blade1HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade1(activity)."
    ::= { blade1HDDSlotEntry 12 }

blade1HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade1(status)."
    ::= { blade1HDDSlotEntry 13 }

blade1HDDSlotHDDFWInfoName    OBJECT-TYPE
    SYNTAX    DisplayString 
    MAX-ACCESS    read-only
    STATUS    current
    DESCRIPTION    "This shows the HDD firmware name of HDD slot of server blade1."
    ::= { blade1HDDSlotEntry 20 }

blade1HDDSlotHDDFWInfoCurrentVer    OBJECT-TYPE
    SYNTAX    DisplayString 
    MAX-ACCESS    read-only
    STATUS    current
    DESCRIPTION    "This shows the HDD firmware current version of HDD slot of server blade1."
    ::= { blade1HDDSlotEntry 21 }

blade1HDDSlotHDDFWInfoNextVer    OBJECT-TYPE
    SYNTAX    DisplayString 
    MAX-ACCESS    read-only
    STATUS    current
    DESCRIPTION    "This shows the HDD firmware next version of HDD slot of server blade1."
    ::= { blade1HDDSlotEntry 22 }

Blade1HDDSlotEntry ::= SEQUENCE {
    blade1HDDSlotIndex
        Integer32,
    blade1HDDSlotNum
        Integer32,
    blade1HDDSlotExist
        INTEGER,
    blade1HDDSlotHDDType
        DisplayString,
    blade1HDDSlotHDDProductName
        DisplayString,
    blade1HDDSlotHDDModel
        DisplayString,
    blade1HDDSlotHDDSerialNum
        DisplayString,
    blade1HDDSlotHDDCapacity
        Integer32,
    blade1HDDSlotHDDRPM
        Integer32,
    blade1HDDSlotHDDStatePower
        INTEGER,
    blade1HDDSlotHDDStateHealth
        INTEGER,
    blade1HDDSlotHDDStateLEDACT
        INTEGER,
    blade1HDDSlotHDDStateLEDSTS
        INTEGER,
    blade1HDDSlotHDDFWInfoName
        DisplayString,
    blade1HDDSlotHDDFWInfoCurrentVer
        DisplayString,
    blade1HDDSlotHDDFWInfoNextVer
        DisplayString
}

blade1ExpansionHDDSlotTable    OBJECT-TYPE
    SYNTAX SEQUENCE OF blade1ExpansionHDDSlotEntry
    MAX-ACCESS not-accessible
    STATUS     current
    DESCRIPTION "This shows the table of expansion HDD slot of server blade1."
    ::= { blade1Install 8 }

blade1ExpansionHDDSlotEntry    OBJECT-TYPE
    SYNTAX Blade1ExpansionHDDSlotEntry
    MAX-ACCESS not-accessible
    STATUS    current
    DESCRIPTION "This shows the entry of expansion HDD slot of server blade1."
    INDEX { blade1ExpansionHDDSlotIndex }
    ::= { blade1ExpansionHDDSlotTable 1 }

blade1ExpansionHDDSlotIndex    OBJECT-TYPE
    SYNTAX    Integer32
    MAX-ACCESS    read-only
    STATUS    current
    DESCRIPTION    "This shows the index of expansion HDD slot of server blade1."
    ::= { blade1ExpansionHDDSlotEntry 1 }

blade1ExpansionHDDSlotNum    OBJECT-TYPE
    SYNTAX    Integer32
    MAX-ACCESS    read-only
    STATUS    current
    DESCRIPTION    "This shows the number of expansion HDD slots of server blade1."
    ::= { blade1ExpansionHDDSlotEntry 2 }

blade1ExpansionHDDSlotExist    OBJECT-TYPE
    SYNTAX    INTEGER {
    non-exist(1), exist(2), unknown(3)
    }
    MAX-ACCESS    read-only
    STATUS    current
    DESCRIPTION    "This shows the registrated state of expansion HDD slot of server blade1."
    ::= { blade1ExpansionHDDSlotEntry 3 }

blade1ExpansionHDDSlotHDDType    OBJECT-TYPE
    SYNTAX    DisplayString 
    MAX-ACCESS    read-only
    STATUS    current
    DESCRIPTION    "This shows the HDD type of expansion HDD slot of server blade1."
    ::= { blade1ExpansionHDDSlotEntry 4 }

blade1ExpansionHDDSlotHDDProductName    OBJECT-TYPE
    SYNTAX    DisplayString 
    MAX-ACCESS    read-only
    STATUS    current
    DESCRIPTION    "This shows the HDD product name of expansion HDD slot of server blade1."
    ::= { blade1ExpansionHDDSlotEntry 5 }

blade1ExpansionHDDSlotHDDModel    OBJECT-TYPE
    SYNTAX    DisplayString 
    MAX-ACCESS    read-only
    STATUS    current
    DESCRIPTION    "This shows the HDD model of expansion HDD slot of server blade1."
    ::= { blade1ExpansionHDDSlotEntry 6 }

blade1ExpansionHDDSlotHDDSerialNum    OBJECT-TYPE
    SYNTAX    DisplayString 
    MAX-ACCESS    read-only
    STATUS    current
    DESCRIPTION    "This shows the HDD serial number of expansion HDD slot of server blade1."
    ::= { blade1ExpansionHDDSlotEntry 7 }

blade1ExpansionHDDSlotHDDCapacity    OBJECT-TYPE
    SYNTAX    Integer32
    UNITS    "GB"
    MAX-ACCESS    read-only
    STATUS    current
    DESCRIPTION    "This shows the HDD capacity of expansion HDD slots of server blade1."
    ::= { blade1ExpansionHDDSlotEntry 8 }

blade1ExpansionHDDSlotHDDRPM    OBJECT-TYPE
    SYNTAX    Integer32
    UNITS    "rpm"
    MAX-ACCESS    read-only
    STATUS    current
    DESCRIPTION    "This shows the HDD drive speed of expansion HDD slot of server blade1."
    ::= { blade1ExpansionHDDSlotEntry 9 }

blade1ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade1."
    ::= { blade1ExpansionHDDSlotEntry 10 }

blade1ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade1."
    ::= { blade1ExpansionHDDSlotEntry 11 }

blade1ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade1(activity)."
    ::= { blade1ExpansionHDDSlotEntry 12 }

blade1ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade1(status)."
    ::= { blade1ExpansionHDDSlotEntry 13 }

blade1ExpansionHDDSlotHDDFWInfoName    OBJECT-TYPE
    SYNTAX    DisplayString 
    MAX-ACCESS    read-only
    STATUS    current
    DESCRIPTION    "This shows the HDD firmware name of expansion HDD slot of server blade1."
    ::= { blade1ExpansionHDDSlotEntry 20 }

blade1ExpansionHDDSlotHDDFWInfoCurrentVer    OBJECT-TYPE
    SYNTAX    DisplayString 
    MAX-ACCESS    read-only
    STATUS    current
    DESCRIPTION    "This shows the HDD firmware current version of expansion HDD slot of server blade1."
    ::= { blade1ExpansionHDDSlotEntry 21 }

blade1ExpansionHDDSlotHDDFWInfoNextVer    OBJECT-TYPE
    SYNTAX    DisplayString 
    MAX-ACCESS    read-only
    STATUS    current
    DESCRIPTION    "This shows the HDD firmware next version of expansion HDD slot of server blade1."
    ::= { blade1ExpansionHDDSlotEntry 22 }

Blade1ExpansionHDDSlotEntry ::= SEQUENCE {
    blade1ExpansionHDDSlotIndex
        Integer32,
    blade1ExpansionHDDSlotNum
        Integer32,
    blade1ExpansionHDDSlotExist
        INTEGER,
    blade1ExpansionHDDSlotHDDType
        DisplayString,
    blade1ExpansionHDDSlotHDDProductName
        DisplayString,
    blade1ExpansionHDDSlotHDDModel
        DisplayString,
    blade1ExpansionHDDSlotHDDSerialNum
        DisplayString,
    blade1ExpansionHDDSlotHDDCapacity
        Integer32,
    blade1ExpansionHDDSlotHDDRPM
        Integer32,
    blade1ExpansionHDDSlotHDDStatePower
        INTEGER,
    blade1ExpansionHDDSlotHDDStateHealth
        INTEGER,
    blade1ExpansionHDDSlotHDDStateLEDACT
        INTEGER,
    blade1ExpansionHDDSlotHDDStateLEDSTS
        INTEGER,
    blade1ExpansionHDDSlotHDDFWInfoName
        DisplayString,
    blade1ExpansionHDDSlotHDDFWInfoCurrentVer
        DisplayString,
    blade1ExpansionHDDSlotHDDFWInfoNextVer
        DisplayString
}

blade1VoltageSensorTable    OBJECT-TYPE
    SYNTAX SEQUENCE OF blade1VoltageSensorEntry
    MAX-ACCESS not-accessible
    STATUS     current
    DESCRIPTION "This shows the table of voltage sensor of server blade1."
    ::= { blade1State 40 }

blade1VoltageSensorEntry    OBJECT-TYPE
    SYNTAX Blade1VoltageSensorEntry
    MAX-ACCESS not-accessible
    STATUS    current
    DESCRIPTION "This shows the entry of voltage sensor of server blade1."
    INDEX { blade1VoltageSensorIndex }
    ::= { blade1VoltageSensorTable 1 }

blade1VoltageSensorIndex    OBJECT-TYPE
    SYNTAX    Integer32
    MAX-ACCESS    read-only
    STATUS    current
    DESCRIPTION    "This shows the index of voltage sensor of server blade1."
    ::= { blade1VoltageSensorEntry 1 }

blade1VoltageSensorName    OBJECT-TYPE
    SYNTAX    DisplayString 
    MAX-ACCESS    read-only
    STATUS    current
    DESCRIPTION    "This shows the voltage sensor name of server blade1."
    ::= { blade1VoltageSensorEntry 2 }

blade1VoltageSensorValue    OBJECT-TYPE
    SYNTAX    Integer32
    UNITS    "0.1 V"
    MAX-ACCESS    read-only
    STATUS    current
    DESCRIPTION    "This shows the voltage sensor value of server blade1."
    ::= { blade1VoltageSensorEntry 3 }

blade1VoltageSensorValid    OBJECT-TYPE
    SYNTAX    INTEGER {
    invalid (1),valid (2),unknown (3)
    }
    MAX-ACCESS    read-only
    STATUS    current
    DESCRIPTION    "This shows the validity of voltage sensor value of server blade1."
    ::= { blade1VoltageSensorEntry 4 }

Blade1VoltageSensorEntry ::= SEQUENCE {
    blade1VoltageSensorIndex
        Integer32,
    blade1VoltageSensorName
        DisplayString,
    blade1VoltageSensorValue
        Integer32,
    blade1VoltageSensorValid
        INTEGER
}

blade1TempSensorTable    OBJECT-TYPE
    SYNTAX SEQUENCE OF blade1TempSensorEntry
    MAX-ACCESS not-accessible
    STATUS     current
    DESCRIPTION "This shows the table of temperature sensor of server blade1."
    ::= { blade1State 41 }

blade1TempSensorEntry    OBJECT-TYPE
    SYNTAX Blade1TempSensorEntry
    MAX-ACCESS not-accessible
    STATUS    current
    DESCRIPTION "This shows the entry of temperature sensor of server blade1."
    INDEX { blade1TempSensorIndex }
    ::= { blade1TempSensorTable 1 }

blade1TempSensorIndex    OBJECT-TYPE
    SYNTAX    Integer32
    MAX-ACCESS    read-only
    STATUS    current
    DESCRIPTION    "This shows the index of temperature sensor of server blade1."
    ::= { blade1TempSensorEntry 1 }

blade1TempSensorName    OBJECT-TYPE
    SYNTAX    DisplayString 
    MAX-ACCESS    read-only
    STATUS    current
    DESCRIPTION    "This shows the temperature sensor name of server blade1."
    ::= { blade1TempSensorEntry 2 }

blade1TempSensorValue    OBJECT-TYPE
    SYNTAX    Integer32
    UNITS    "0.1 degrees C"
    MAX-ACCESS    read-only
    STATUS    current
    DESCRIPTION    "This shows the temperature sensor value of server blade1."
    ::= { blade1TempSensorEntry 3 }

blade1TempSensorValid    OBJECT-TYPE
    SYNTAX    INTEGER {
    invalid (1),valid (2),unknown (3)
    }
    MAX-ACCESS    read-only
    STATUS    current
    DESCRIPTION    "This shows the validity of temperature sensor value of server blade1."
    ::= { blade1TempSensorEntry 4 }

Blade1TempSensorEntry ::= SEQUENCE {
    blade1TempSensorIndex
        Integer32,
    blade1TempSensorName
        DisplayString,
    blade1TempSensorValue
        Integer32,
    blade1TempSensorValid
        INTEGER
}

blade1FWInfo    OBJECT IDENTIFIER ::= { blade1 5 } 

blade1FWInfoTotalCurrentVer    OBJECT-TYPE
    SYNTAX    DisplayString (SIZE(0..40))
    MAX-ACCESS    read-only
    STATUS    current
    DESCRIPTION    "This shows the total current version of firmware of server blade1."
    ::= { blade1FWInfo 1 }

blade1FWInfoTotalNextVer    OBJECT-TYPE
    SYNTAX    DisplayString (SIZE(0..40))
    MAX-ACCESS    read-only
    STATUS    current
    DESCRIPTION    "This shows the total next version of firmware of server blade1."
    ::= { blade1FWInfo 2 }

blade1FWInfoTable    OBJECT-TYPE
    SYNTAX SEQUENCE OF blade1FWInfoEntry
    MAX-ACCESS not-accessible
    STATUS     current
    DESCRIPTION "This shows the table of firmware information of server blade1."
    ::= { blade1FWInfo 3 }

blade1FWInfoEntry    OBJECT-TYPE
    SYNTAX Blade1FWInfoEntry
    MAX-ACCESS not-accessible
    STATUS    current
    DESCRIPTION "This shows the entry of firmware information of server blade1."
    INDEX { blade1FWInfoIndex }
    ::= { blade1FWInfoTable 1 }

blade1FWInfoIndex    OBJECT-TYPE
    SYNTAX    Integer32
    MAX-ACCESS    read-only
    STATUS    current
    DESCRIPTION    "This shows the index of firmware information of server blade1."
    ::= { blade1FWInfoEntry 1 }

blade1FWInfoName    OBJECT-TYPE
    SYNTAX    DisplayString (SIZE(0..40))
    MAX-ACCESS    read-only
    STATUS    current
    DESCRIPTION    "This shows the firmware name of server blade1."
    ::= { blade1FWInfoEntry 2 }

blade1FWCurrentVer    OBJECT-TYPE
    SYNTAX    DisplayString (SIZE(0..40))
    MAX-ACCESS    read-only
    STATUS    current
    DESCRIPTION    "This shows the firmware current version of server blade1."
    ::= { blade1FWInfoEntry 3 }

blade1FWInfoNextVer    OBJECT-TYPE
    SYNTAX    DisplayString (SIZE(0..40))
    MAX-ACCESS    read-only
    STATUS    current
    DESCRIPTION    "This shows the firmware next version of server blade1."
    ::= { blade1FWInfoEntry 4 }

blade1FWInfoHVMCurrentVer    OBJECT-TYPE
    SYNTAX    DisplayString (SIZE(0..40))
    MAX-ACCESS    read-only
    STATUS    current
    DESCRIPTION    "This shows the HVM current version of server blade1."
    ::= { blade1FWInfo 4 }

blade1FWInfoHVMNextVer    OBJECT-TYPE
    SYNTAX    DisplayString (SIZE(0..40))
    MAX-ACCESS    read-only
    STATUS    current
    DESCRIPTION    "This shows the HVM next version of server blade1."
    ::= { blade1FWInfo 5 }

Blade1FWInfoEntry ::= SEQUENCE {
    blade1FWInfoIndex
        Integer32,
    blade1FWInfoName
        DisplayString,
    blade1FWCurrentVer
        DisplayString,
    blade1FWInfoNextVer
        DisplayString,
    blade1FWInfoHVMCurrentVer
        DisplayString,
    blade1FWInfoHVMNextVer
        DisplayString
}

blade2    OBJECT IDENTIFIER ::= { blade 2 } 

blade2BasicInfo    OBJECT IDENTIFIER ::= { blade2 1 } 

blade2InfoProductName    OBJECT-TYPE
    SYNTAX    DisplayString (SIZE(0..40))
    MAX-ACCESS    read-only
    STATUS    current
    DESCRIPTION    "This shows the product name of server blade2."
    ::= { blade2BasicInfo 1 }

blade2InfoModel    OBJECT-TYPE
    SYNTAX    DisplayString (SIZE(0..40))
    MAX-ACCESS    read-only
    STATUS    current
    DESCRIPTION    "This shows the model name of server blade2."
    ::= { blade2BasicInfo 2 }

blade2InfoSerialNum    OBJECT-TYPE
    SYNTAX    DisplayString (SIZE(0..40))
    MAX-ACCESS    read-only
    STATUS    current
    DESCRIPTION    "This shows the serial number of server blade2."
    ::= { blade2BasicInfo 3 }

blade2InfoProductVersion    OBJECT-TYPE
    SYNTAX    DisplayString (SIZE(0..40))
    MAX-ACCESS    read-only
    STATUS    current
    DESCRIPTION    "This shows the product version of server blade2."
    ::= { blade2BasicInfo 4 }

blade2InfoProductManufacturer    OBJECT-TYPE
    SYNTAX    DisplayString (SIZE(0..40))
    MAX-ACCESS    read-only
    STATUS    current
    DESCRIPTION    "This shows the product manufacturer of server blade2."
    ::= { blade2BasicInfo 5 }

blade2InfoBoardProductName    OBJECT-TYPE
    SYNTAX    DisplayString (SIZE(0..40))
    MAX-ACCESS    read-only
    STATUS    current
    DESCRIPTION    "This shows the board product name of server blade2."
    ::= { blade2BasicInfo 7 }

blade2InfoBoardSerialNum    OBJECT-TYPE
    SYNTAX    DisplayString (SIZE(0..40))
    MAX-ACCESS    read-only
    STATUS    current
    DESCRIPTION    "This shows the board serial number of server blade2."
    ::= { blade2BasicInfo 8 }

blade2InfoBoardManufacturer    OBJECT-TYPE
    SYNTAX    DisplayString (SIZE(0..40))
    MAX-ACCESS    read-only
    STATUS    current
    DESCRIPTION    "This shows the board manufacturer of server blade2."
    ::= { blade2BasicInfo 9 }

blade2InfoUUID    OBJECT-TYPE
    SYNTAX    DisplayString (SIZE(0..40))
    MAX-ACCESS    read-only
    STATUS    current
    DESCRIPTION    "This shows UUID(universal Unique ID) of server blade2."
    ::= { blade2BasicInfo 10 }

blade2InfoLogicalPartitionSupport    OBJECT-TYPE
    SYNTAX    INTEGER {
    not-support(1), support(2),unknown(3)
    }
    MAX-ACCESS    read-only
    STATUS    current
    DESCRIPTION    "This shows whether the server blade2 supports HVM or not of server blade1."
    ::= { blade2BasicInfo 11 }

blade2InfoRemoteKVMSupport    OBJECT-TYPE
    SYNTAX    INTEGER {
    not-support(1), support(2),unknown(3)
    }
    MAX-ACCESS    read-only
    STATUS    current
    DESCRIPTION    "This shows whether the server blade2 supports remote KVM or not of server blade1."
    ::= { blade2BasicInfo 12 }

blade2InfoSpec    OBJECT IDENTIFIER ::= { blade2BasicInfo 20 } 

blade2SpecInputCurrentType    OBJECT-TYPE
    SYNTAX    INTEGER {
    ac(1),dc(2),unknown(3)
    }
    MAX-ACCESS    read-only
    STATUS    current
    DESCRIPTION    "This shows the currency type of server blade2."
    ::= { blade2InfoSpec 1 }

blade2SpecRateVoltage    OBJECT-TYPE
    SYNTAX    Integer32
    UNITS    "0.1 V"
    MAX-ACCESS    read-only
    STATUS    current
    DESCRIPTION    "This shows the rated voltage of server blade2."
    ::= { blade2InfoSpec 2 }

blade2SpecConsumptionCurrent    OBJECT-TYPE
    SYNTAX    Integer32
    UNITS    "0.1 A"
    MAX-ACCESS    read-only
    STATUS    current
    DESCRIPTION    "This shows the consumption current of server blade2."
    ::= { blade2InfoSpec 3 }

blade2SpecPowerConsumption    OBJECT-TYPE
    SYNTAX    Integer32
    UNITS    "W"
    MAX-ACCESS    read-only
    STATUS    current
    DESCRIPTION    "This shows the power consumption of server blade2."
    ::= { blade2InfoSpec 4 }

blade2SpecMass    OBJECT-TYPE
    SYNTAX    Integer32
    UNITS    "0.1 kg"
    MAX-ACCESS    read-only
    STATUS    current
    DESCRIPTION    "This shows the weight of server blade2."
    ::= { blade2InfoSpec 5 }

blade2InfoUpperLimitIntakeTemp    OBJECT-TYPE
    SYNTAX    Integer32
    UNITS    "0.1 degrees C"
    MAX-ACCESS    read-only
    STATUS    current
    DESCRIPTION    "This shows the maximum limited intake temperature of server blade2."
    ::= { blade2InfoSpec 6 }

blade2InfoLowerLimitIntakeTemp    OBJECT-TYPE
    SYNTAX    Integer32
    UNITS    "0.1 degrees C"
    MAX-ACCESS    read-only
    STATUS    current
    DESCRIPTION    "This shows the minimum limited intake temperature of server blade2."
    ::= { blade2InfoSpec 7 }

blade2SpecSize    OBJECT-TYPE
    SYNTAX    DisplayString (SIZE(0..40))
    MAX-ACCESS    read-only
    STATUS    current
    DESCRIPTION    "This shows the size of server blade2."
    ::= { blade2InfoSpec 8 }

blade2SpecOccupySlots    OBJECT-TYPE
    SYNTAX    Integer32
    MAX-ACCESS    read-only
    STATUS    current
    DESCRIPTION    "This shows the dedicated number of slots of server blade2."
    ::= { blade2InfoSpec 9 }

blade2SpecExpansionBladeSlot    OBJECT-TYPE
    SYNTAX    Integer32
    MAX-ACCESS    read-only
    STATUS    current
    DESCRIPTION    "This shows the number of slots of expansion blade of server blade2."
    ::= { blade2InfoSpec 10 }

blade2InfoExpansionBladeTable    OBJECT-TYPE
    SYNTAX SEQUENCE OF blade2InfoExpansionBladeEntry
    MAX-ACCESS not-accessible
    STATUS     current
    DESCRIPTION "This shows the table of expansion blade slot of server blade2."
    ::= { blade2BasicInfo 30 }

blade2InfoExpansionBladeEntry    OBJECT-TYPE
    SYNTAX Blade2InfoExpansionBladeEntry
    MAX-ACCESS not-accessible
    STATUS    current
    DESCRIPTION "This shows the entry of expansion blade slot of server blade2."
    INDEX { blade2InfoExpansionBladeIndex }
    ::= { blade2InfoExpansionBladeTable 1 }

blade2InfoExpansionBladeIndex    OBJECT-TYPE
    SYNTAX    Integer32
    MAX-ACCESS    read-only
    STATUS    current
    DESCRIPTION    "This shows the index of expansion blade slot of server blade2."
    ::= { blade2InfoExpansionBladeEntry 1 }

blade2InfoExpansionBladeExist    OBJECT-TYPE
    SYNTAX    INTEGER {
    non-exist(1), exist(2), unknown(3)
    }
    MAX-ACCESS    read-only
    STATUS    current
    DESCRIPTION    "This shows the registrated state of expansion blade of server blade2."
    ::= { blade2InfoExpansionBladeEntry 2 }

blade2InfoExpansionBladeProductName    OBJECT-TYPE
    SYNTAX    DisplayString (SIZE(0..40))
    MAX-ACCESS    read-only
    STATUS    current
    DESCRIPTION    "This shows the product name of expansion blade of server blade2."
    ::= { blade2InfoExpansionBladeEntry 3 }

blade2InfoExpansionBladeModel    OBJECT-TYPE
    SYNTAX    DisplayString (SIZE(0..40))
    MAX-ACCESS    read-only
    STATUS    current
    DESCRIPTION    "This shows the model name of expansion blade of server blade2."
    ::= { blade2InfoExpansionBladeEntry 4 }

blade2InfoExpansionBladeSerialNum    OBJECT-TYPE
    SYNTAX    DisplayString (SIZE(0..40))
    MAX-ACCESS    read-only
    STATUS    current
    DESCRIPTION    "This shows the serial number of expansion blade of server blade2."
    ::= { blade2InfoExpansionBladeEntry 5 }

blade2InfoExpansionBladeProductVersion    OBJECT-TYPE
    SYNTAX    DisplayString (SIZE(0..40))
    MAX-ACCESS    read-only
    STATUS    current
    DESCRIPTION    "This shows the product version of expansion blade of server blade2."
    ::= { blade2InfoExpansionBladeEntry 6 }

blade2InfoExpansionBladeProductManufacturer    OBJECT-TYPE
    SYNTAX    DisplayString (SIZE(0..40))
    MAX-ACCESS    read-only
    STATUS    current
    DESCRIPTION    "This shows the product manufacturer of expansion blade of server blade2."
    ::= { blade2InfoExpansionBladeEntry 7 }

blade2InfoExpansionBladeBoardProductName    OBJECT-TYPE
    SYNTAX    DisplayString (SIZE(0..40))
    MAX-ACCESS    read-only
    STATUS    current
    DESCRIPTION    "This shows the board product name of expansion blade of server blade2."
    ::= { blade2InfoExpansionBladeEntry 9 }

blade2InfoExpansionBladeBoardSerialNum    OBJECT-TYPE
    SYNTAX    DisplayString (SIZE(0..40))
    MAX-ACCESS    read-only
    STATUS    current
    DESCRIPTION    "This shows the board serial number of expansion blade of server blade2."
    ::= { blade2InfoExpansionBladeEntry 10 }

blade2InfoExpansionBladeBoardManufacturer    OBJECT-TYPE
    SYNTAX    DisplayString (SIZE(0..40))
    MAX-ACCESS    read-only
    STATUS    current
    DESCRIPTION    "This shows the board manufacturer of expansion blade of server blade2."
    ::= { blade2InfoExpansionBladeEntry 11 }

Blade2InfoExpansionBladeEntry ::= SEQUENCE {
    blade2InfoExpansionBladeIndex
        Integer32,
    blade2InfoExpansionBladeExist
        INTEGER,
    blade2InfoExpansionBladeProductName
        DisplayString,
    blade2InfoExpansionBladeModel
        DisplayString,
    blade2InfoExpansionBladeSerialNum
        DisplayString,
    blade2InfoExpansionBladeProductVersion
        DisplayString,
    blade2InfoExpansionBladeProductManufacturer
        DisplayString,
    blade2InfoExpansionBladeBoardProductName
        DisplayString,
    blade2InfoExpansionBladeBoardSerialNum
        DisplayString,
    blade2InfoExpansionBladeBoardManufacturer
        DisplayString
}

blade2Capacity    OBJECT IDENTIFIER ::= { blade2 2 } 

blade2CapacityCPUSocket    OBJECT-TYPE
    SYNTAX    Integer32
    MAX-ACCESS    read-only
    STATUS    current
    DESCRIPTION    "This shows the capacity of CPU sockets of server blade2."
    ::= { blade2Capacity 1 }

blade2CapacityDIMMSlot    OBJECT-TYPE
    SYNTAX    Integer32
    MAX-ACCESS    read-only
    STATUS    current
    DESCRIPTION    "This shows the capacity of DIMM slots of server blade2."
    ::= { blade2Capacity 2 }

blade2CapacityPCISlot    OBJECT-TYPE
    SYNTAX    Integer32
    MAX-ACCESS    read-only
    STATUS    current
    DESCRIPTION    "This shows the capacity of PCI slots of server blade2."
    ::= { blade2Capacity 3 }

blade2CapacityLOM    OBJECT-TYPE
    SYNTAX    Integer32
    MAX-ACCESS    read-only
    STATUS    current
    DESCRIPTION    "This shows the capacity of onboard LAN ports of server blade2."
    ::= { blade2Capacity 4 }

blade2CapacityFan    OBJECT-TYPE
    SYNTAX    Integer32
    MAX-ACCESS    read-only
    STATUS    current
    DESCRIPTION    "This shows the capacity of onboard fans of server blade2."
    ::= { blade2Capacity 5 }

blade2CapacityHDDSlot    OBJECT-TYPE
    SYNTAX    Integer32
    MAX-ACCESS    read-only
    STATUS    current
    DESCRIPTION    "This shows the capacity of HDD slots of server blade2."
    ::= { blade2Capacity 6 }

blade2CapacityVoltageSensor    OBJECT-TYPE
    SYNTAX    Integer32
    MAX-ACCESS    read-only
    STATUS    current
    DESCRIPTION    "This shows the capacity of voltage sensors of blade2."
    ::= { blade2Capacity 7 }

blade2CapacityTempSensor    OBJECT-TYPE
    SYNTAX    Integer32
    MAX-ACCESS    read-only
    STATUS    current
    DESCRIPTION    "This shows the capacity of temperature sensors of blade2."
    ::= { blade2Capacity 8 }

blade2CapacityExpansionHDDSlot    OBJECT-TYPE
    SYNTAX    Integer32
    MAX-ACCESS    read-only
    STATUS    current
    DESCRIPTION    "This shows the capacity of expansion HDD slots of server blade2."
    ::= { blade2Capacity 9 }

blade2CapacityLED    OBJECT-TYPE
    SYNTAX    Integer32
    MAX-ACCESS    read-only
    STATUS    current
    DESCRIPTION    "This shows the capacity of count of LEDs of server blade2."
    ::= { blade2Capacity 10 }

blade2Settings    OBJECT IDENTIFIER ::= { blade2 3 } 

blade2SettingsBelongPartitionNum    OBJECT-TYPE
    SYNTAX    Integer32
    MAX-ACCESS    read-only
    STATUS    current
    DESCRIPTION    "This shows the partition number of server blade2."
    ::= { blade2Settings 1 }

blade2SettingsDetailHVMLicenceModel    OBJECT-TYPE
    SYNTAX    DisplayString (SIZE(0..40))
    MAX-ACCESS    read-only
    STATUS    current
    DESCRIPTION    "This shows the HVM licence of detailed server blade2 (model). "
    ::= { blade2Settings 2 }

blade2SettingsDetailHVMLicenceAvailableVersion    OBJECT-TYPE
    SYNTAX    DisplayString (SIZE(0..40))
    MAX-ACCESS    read-only
    STATUS    current
    DESCRIPTION    "This shows the HVM licence of detailed server blade2 (available version). "
    ::= { blade2Settings 3 }

blade2SettingsManagementPortIPAddress    OBJECT-TYPE
    SYNTAX    DisplayString (SIZE(0..40))
    MAX-ACCESS    read-only
    STATUS    current
    DESCRIPTION    "This shows the IP address of management port of server blade2."
    ::= { blade2Settings 4 }

blade2State    OBJECT IDENTIFIER ::= { blade2 4 } 

blade2StateSlotNum    OBJECT-TYPE
    SYNTAX    Integer32
    MAX-ACCESS    read-only
    STATUS    current
    DESCRIPTION    "This shows the number of installed slots of server blade2."
    ::= { blade2State 1 }

blade2StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade2."
    ::= { blade2State 2 }

blade2StateHealth    OBJECT-TYPE
    SYNTAX    INTEGER {
    normal (1),fail (2),unknown (3)
    }
    MAX-ACCESS    read-only
    STATUS    current
    DESCRIPTION    "This shows the health state of server blade2."
    ::= { blade2State 3 }

blade2StatePrimaly    OBJECT-TYPE
    SYNTAX    INTEGER {
    primary(1), non-primary(2),unknown(3)
    }
    MAX-ACCESS    read-only
    STATUS    current
    DESCRIPTION    "This shows the primary state of server blade2."
    ::= { blade2State 4 }

blade2StateCurrentVoltage    OBJECT-TYPE
    SYNTAX    Integer32
    UNITS    "0.1 V"
    MAX-ACCESS    read-only
    STATUS    current
    DESCRIPTION    "This shows the current voltage of server blade2."
    ::= { blade2State 5 }

blade2StateConsumptionCurrent    OBJECT-TYPE
    SYNTAX    Integer32
    UNITS    "0.1 A"
    MAX-ACCESS    read-only
    STATUS    current
    DESCRIPTION    "This shows the consumption current of server blade2."
    ::= { blade2State 6 }

blade2StatePowerConsumption    OBJECT-TYPE
    SYNTAX    Integer32
    UNITS    "W"
    MAX-ACCESS    read-only
    STATUS    current
    DESCRIPTION    "This shows the power consumption of server blade2."
    ::= { blade2State 7 }

blade2StateIntakeTemp    OBJECT-TYPE
    SYNTAX    INTEGER {
    normal (1), higher-warning (2), higher-error (3), lower-warning (4), unknown(5)
    }
    MAX-ACCESS    read-only
    STATUS    current
    DESCRIPTION    "This shows the state of intake temperature of server blade2."
    ::= { blade2State 8 }

blade2StateLEDTable    OBJECT-TYPE
    SYNTAX SEQUENCE OF blade2StateLEDEntry
    MAX-ACCESS not-accessible
    STATUS     current
    DESCRIPTION "This shows the table of LED of server blade2."
    ::= { blade2State 9 }

blade2StateLEDEntry    OBJECT-TYPE
    SYNTAX Blade2StateLEDEntry
    MAX-ACCESS not-accessible
    STATUS    current
    DESCRIPTION "This shows the entry of LED of server blade2."
    INDEX { blade2StateLEDIndex }
    ::= { blade2StateLEDTable 1 }

blade2StateLEDIndex    OBJECT-TYPE
    SYNTAX    Integer32
    MAX-ACCESS    read-only
    STATUS    current
    DESCRIPTION    "This shows the index of LED of server blade2."
    ::= { blade2StateLEDEntry 1 }

blade2StateLEDName    OBJECT-TYPE
    SYNTAX    DisplayString (SIZE(0..40))
    MAX-ACCESS    read-only
    STATUS    current
    DESCRIPTION    "This shows the name of LED of server blade2."
    ::= { blade2StateLEDEntry 2 }

blade2StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade2."
    ::= { blade2StateLEDEntry 3 }

blade2StateLEDColor    OBJECT-TYPE
    SYNTAX    INTEGER {
    blue (1),green (2),red (3),amber (4),unknown (5)
    }
    MAX-ACCESS    read-only
    STATUS    current
    DESCRIPTION    "This shows the color of LED of server blade2."
    ::= { blade2StateLEDEntry 4 }

Blade2StateLEDEntry ::= SEQUENCE {
    blade2StateLEDIndex
        Integer32,
    blade2StateLEDName
        DisplayString,
    blade2StateLEDState
        INTEGER,
    blade2StateLEDColor
        INTEGER
}

blade2StateOther    OBJECT IDENTIFIER ::= { blade2State 20 } 

blade2MaintMode    OBJECT-TYPE
    SYNTAX    INTEGER {
    Normal(1), CE-Maint-mode(2), User-Maint-mode(3), unknown(4)
    }
    MAX-ACCESS    read-only
    STATUS    current
    DESCRIPTION    "This shows the maintenance mode of server blade2."
    ::= { blade2StateOther 1 }

blade2Install    OBJECT IDENTIFIER ::= { blade2State 30 } 

blade2InsCPUSocketTable    OBJECT-TYPE
    SYNTAX SEQUENCE OF blade2InsCPUSocketEntry
    MAX-ACCESS not-accessible
    STATUS     current
    DESCRIPTION "This shows the table of CPU socket of server blade2."
    ::= { blade2Install 1 }

blade2InsCPUSocketEntry    OBJECT-TYPE
    SYNTAX Blade2InsCPUSocketEntry
    MAX-ACCESS not-accessible
    STATUS    current
    DESCRIPTION "This shows the entry of CPU socket of server blade2."
    INDEX { blade2InsCPUSocketIndex }
    ::= { blade2InsCPUSocketTable 1 }

blade2InsCPUSocketIndex    OBJECT-TYPE
    SYNTAX    Integer32
    MAX-ACCESS    read-only
    STATUS    current
    DESCRIPTION    "This shows the index of CPU socket of server blade2."
    ::= { blade2InsCPUSocketEntry 1 }

blade2InsCPUSocketNum    OBJECT-TYPE
    SYNTAX    Integer32
    MAX-ACCESS    read-only
    STATUS    current
    DESCRIPTION    "This shows the number of CPU sockets of server blade2."
    ::= { blade2InsCPUSocketEntry 2 }

blade2InsCPUSocketExist    OBJECT-TYPE
    SYNTAX    INTEGER {
    non-exist(1), exist(2), unknown(3)
    }
    MAX-ACCESS    read-only
    STATUS    current
    DESCRIPTION    "This shows the registrated state of CPU socket of server blade2."
    ::= { blade2InsCPUSocketEntry 3 }

blade2InsCPUSocketCPUName    OBJECT-TYPE
    SYNTAX    DisplayString (SIZE(0..40))
    MAX-ACCESS    read-only
    STATUS    current
    DESCRIPTION    "This shows the CPU name of CPU socket of server blade2."
    ::= { blade2InsCPUSocketEntry 4 }

blade2InsCPUSocketCPUFrequency    OBJECT-TYPE
    SYNTAX    Integer32
    UNITS    "MHz"
    MAX-ACCESS    read-only
    STATUS    current
    DESCRIPTION    "This shows the CPU frequency of CPU socket of server blade2."
    ::= { blade2InsCPUSocketEntry 5 }

blade2InsCPUSocketCPUStepping    OBJECT-TYPE
    SYNTAX    DisplayString 
    MAX-ACCESS    read-only
    STATUS    current
    DESCRIPTION    "This shows the CPU stepping of CPU socket of server blade2."
    ::= { blade2InsCPUSocketEntry 6 }

blade2InsCPUSocketCPUCoreNum    OBJECT-TYPE
    SYNTAX    Integer32
    MAX-ACCESS    read-only
    STATUS    current
    DESCRIPTION    "This shows the CPU core number of CPU socket of server blade2."
    ::= { blade2InsCPUSocketEntry 7 }

blade2InsCPUSocketCPUUpperLimitTemp    OBJECT-TYPE
    SYNTAX    Integer32
    UNITS    "0.1 degrees C"
    MAX-ACCESS    read-only
    STATUS    current
    DESCRIPTION    "This shows the maximum limited CPU temperature of server blade2."
    ::= { blade2InsCPUSocketEntry 8 }

blade2InsCPUSocketCPULowerLimitTemp    OBJECT-TYPE
    SYNTAX    Integer32
    UNITS    "0.1 degrees C"
    MAX-ACCESS    read-only
    STATUS    current
    DESCRIPTION    "This shows the minimum limited CPU temperature of server blade2."
    ::= { blade2InsCPUSocketEntry 9 }

blade2InsDIMMCapacity    OBJECT-TYPE
    SYNTAX    Integer32
    UNITS    "GB"
    MAX-ACCESS    read-only
    STATUS    current
    DESCRIPTION    "This shows the total amount of DIMM capacity of server blade2."
    ::= { blade2Install 2 }

Blade2InsCPUSocketEntry ::= SEQUENCE {
    blade2InsCPUSocketIndex
        Integer32,
    blade2InsCPUSocketNum
        Integer32,
    blade2InsCPUSocketExist
        INTEGER,
    blade2InsCPUSocketCPUName
        DisplayString,
    blade2InsCPUSocketCPUFrequency
        Integer32,
    blade2InsCPUSocketCPUStepping
        DisplayString,
    blade2InsCPUSocketCPUCoreNum
        Integer32,
    blade2InsCPUSocketCPUUpperLimitTemp
        Integer32,
    blade2InsCPUSocketCPULowerLimitTemp
        Integer32,
    blade2InsDIMMCapacity
        Integer32
}

blade2InsDIMMSlotTable    OBJECT-TYPE
    SYNTAX SEQUENCE OF blade2InsDIMMSlotEntry
    MAX-ACCESS not-accessible
    STATUS     current
    DESCRIPTION "This shows the table of DIMM slot of server blade2."
    ::= { blade2Install 3 }

blade2InsDIMMSlotEntry    OBJECT-TYPE
    SYNTAX Blade2InsDIMMSlotEntry
    MAX-ACCESS not-accessible
    STATUS    current
    DESCRIPTION "This shows the entry of DIMM slot of server blade2."
    INDEX { blade2InsDIMMSlotIndex }
    ::= { blade2InsDIMMSlotTable 1 }

blade2InsDIMMSlotIndex    OBJECT-TYPE
    SYNTAX    Integer32
    MAX-ACCESS    read-only
    STATUS    current
    DESCRIPTION    "This shows the index of DIMM slot of server blade2."
    ::= { blade2InsDIMMSlotEntry 1 }

blade2InsDIMMSlotExist    OBJECT-TYPE
    SYNTAX    INTEGER {
    non-exist(1), exist(2), unknown(3)
    }
    MAX-ACCESS    read-only
    STATUS    current
    DESCRIPTION    "This shows the registrated state of DIMM slot of server blade2."
    ::= { blade2InsDIMMSlotEntry 2 }

blade2InsDIMMSlotDIMMCapacity    OBJECT-TYPE
    SYNTAX    Integer32
    UNITS    "GB"
    MAX-ACCESS    read-only
    STATUS    current
    DESCRIPTION    "This shows the capacity of DIMM slots of server blade2."
    ::= { blade2InsDIMMSlotEntry 3 }

blade2InsDIMMSlotDIMMType    OBJECT-TYPE
    SYNTAX    DisplayString 
    MAX-ACCESS    read-only
    STATUS    current
    DESCRIPTION    "This shows the DIMM type of DIMM slot of server blade2."
    ::= { blade2InsDIMMSlotEntry 4 }

blade2InsDIMMSlotDIMMFrequency    OBJECT-TYPE
    SYNTAX    Integer32
    UNITS    "MHz"
    MAX-ACCESS    read-only
    STATUS    current
    DESCRIPTION    "This shows the DIMM frequency of DIMM slot of server blade2."
    ::= { blade2InsDIMMSlotEntry 5 }

blade2InsDIMMSlotDIMMCasLatency    OBJECT-TYPE
    SYNTAX    Integer32
    MAX-ACCESS    read-only
    STATUS    current
    DESCRIPTION    "This shows the DIMM cas latency of DIMM slot of server blade2."
    ::= { blade2InsDIMMSlotEntry 6 }

blade2InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade2."
    ::= { blade2InsDIMMSlotEntry 7 }

Blade2InsDIMMSlotEntry ::= SEQUENCE {
    blade2InsDIMMSlotIndex
        Integer32,
    blade2InsDIMMSlotExist
        INTEGER,
    blade2InsDIMMSlotDIMMCapacity
        Integer32,
    blade2InsDIMMSlotDIMMType
        DisplayString,
    blade2InsDIMMSlotDIMMFrequency
        Integer32,
    blade2InsDIMMSlotDIMMCasLatency
        Integer32,
    blade2InsDIMMSlotDIMMStatus
        INTEGER
}

blade2InsPCISlotTable    OBJECT-TYPE
    SYNTAX SEQUENCE OF blade2InsPCISlotEntry
    MAX-ACCESS not-accessible
    STATUS     current
    DESCRIPTION "This shows the table of PCI slot of server blade2."
    ::= { blade2Install 4 }

blade2InsPCISlotEntry    OBJECT-TYPE
    SYNTAX Blade2InsPCISlotEntry
    MAX-ACCESS not-accessible
    STATUS    current
    DESCRIPTION "This shows the entry of PCI slot of server blade2."
    INDEX { blade2InsPCISlotIndex }
    ::= { blade2InsPCISlotTable 1 }

blade2InsPCISlotIndex    OBJECT-TYPE
    SYNTAX    Integer32
    MAX-ACCESS    read-only
    STATUS    current
    DESCRIPTION    "This shows the index of PCI slot of server blade2."
    ::= { blade2InsPCISlotEntry 1 }

blade2InsPCISlotType    OBJECT-TYPE
    SYNTAX    DisplayString 
    MAX-ACCESS    read-only
    STATUS    current
    DESCRIPTION    "This shows the type of PCI slot of server blade2."
    ::= { blade2InsPCISlotEntry 2 }

blade2InsPCISlotExist    OBJECT-TYPE
    SYNTAX    INTEGER {
    non-exist(1), exist(2), unknown(3)
    }
    MAX-ACCESS    read-only
    STATUS    current
    DESCRIPTION    "This shows the registrated state of PCI slot of server blade2."
    ::= { blade2InsPCISlotEntry 3 }

blade2InsPCISlotPCIType    OBJECT-TYPE
    SYNTAX    DisplayString 
    MAX-ACCESS    read-only
    STATUS    current
    DESCRIPTION    "This shows the PCI type of PCI slot of server blade2."
    ::= { blade2InsPCISlotEntry 4 }

blade2InsPCISlotPCIProductName    OBJECT-TYPE
    SYNTAX    DisplayString 
    MAX-ACCESS    read-only
    STATUS    current
    DESCRIPTION    "This shows the PCI product name of PCI slot of server blade2."
    ::= { blade2InsPCISlotEntry 5 }

blade2InsPCISlotPCISerial    OBJECT-TYPE
    SYNTAX    DisplayString 
    MAX-ACCESS    read-only
    STATUS    current
    DESCRIPTION    "This shows the serial number of PCI slot of server blade2."
    ::= { blade2InsPCISlotEntry 6 }

blade2InsPCISlotPCIManufacturer    OBJECT-TYPE
    SYNTAX    DisplayString 
    MAX-ACCESS    read-only
    STATUS    current
    DESCRIPTION    "This shows the manufacturer of PCI slot of server blade2."
    ::= { blade2InsPCISlotEntry 7 }

blade2InsPCISlotNum    OBJECT-TYPE
    SYNTAX    Integer32
    MAX-ACCESS    read-only
    STATUS    current
    DESCRIPTION    "This shows the number of PCI slots of server blade2."
    ::= { blade2InsPCISlotEntry 8 }

Blade2InsPCISlotEntry ::= SEQUENCE {
    blade2InsPCISlotIndex
        Integer32,
    blade2InsPCISlotType
        DisplayString,
    blade2InsPCISlotExist
        INTEGER,
    blade2InsPCISlotPCIType
        DisplayString,
    blade2InsPCISlotPCIProductName
        DisplayString,
    blade2InsPCISlotPCISerial
        DisplayString,
    blade2InsPCISlotPCIManufacturer
        DisplayString,
    blade2InsPCISlotNum
        Integer32
}

blade2InsLOMTable    OBJECT-TYPE
    SYNTAX SEQUENCE OF blade2InsLOMEntry
    MAX-ACCESS not-accessible
    STATUS     current
    DESCRIPTION "This shows the table of onboard LAN of server blade2."
    ::= { blade2Install 5 }

blade2InsLOMEntry    OBJECT-TYPE
    SYNTAX Blade2InsLOMEntry
    MAX-ACCESS not-accessible
    STATUS    current
    DESCRIPTION "This shows the entry of onboard LAN of server blade2."
    INDEX { blade2InsLOMIndex }
    ::= { blade2InsLOMTable 1 }

blade2InsLOMIndex    OBJECT-TYPE
    SYNTAX    Integer32
    MAX-ACCESS    read-only
    STATUS    current
    DESCRIPTION    "This shows the index of onboard LAN of server blade2."
    ::= { blade2InsLOMEntry 1 }

blade2InsLOMType    OBJECT-TYPE
    SYNTAX    DisplayString 
    MAX-ACCESS    read-only
    STATUS    current
    DESCRIPTION    "This shows the type of onboard LAN of server blade2."
    ::= { blade2InsLOMEntry 2 }

blade2InsLOMLinkSpeed    OBJECT-TYPE
    SYNTAX    Integer32
    UNITS    "bps"
    MAX-ACCESS    read-only
    STATUS    current
    DESCRIPTION    "This shows the link speed of onboard LAN of server blade2."
    ::= { blade2InsLOMEntry 3 }

blade2InsLOMMAC    OBJECT-TYPE
    SYNTAX    DisplayString 
    MAX-ACCESS    read-only
    STATUS    current
    DESCRIPTION    "This shows the MAC address of onboard LAN of server blade2."
    ::= { blade2InsLOMEntry 4 }

blade2InsLOMLinkStatus    OBJECT-TYPE
    SYNTAX    INTEGER {
    up (1),down (2),unknown (3)
    }
    MAX-ACCESS    read-only
    STATUS    current
    DESCRIPTION    "This shows the link state of onboard LAN of server blade2."
    ::= { blade2InsLOMEntry 5 }

blade2InsLOMPortDivide    OBJECT-TYPE
    SYNTAX    INTEGER {
    possible (1),Impossible (2),unknown (3)
    }
    MAX-ACCESS    read-only
    STATUS    current
    DESCRIPTION    "This shows the port divide propriety of onboard LAN of server blade2."
    ::= { blade2InsLOMEntry 6 }

blade2InsLOMPortDivideNum    OBJECT-TYPE
    SYNTAX    Integer32
    MAX-ACCESS    read-only
    STATUS    current
    DESCRIPTION    "This shows the port divide number of onboard LAN of server blade2."
    ::= { blade2InsLOMEntry 7 }

Blade2InsLOMEntry ::= SEQUENCE {
    blade2InsLOMIndex
        Integer32,
    blade2InsLOMType
        DisplayString,
    blade2InsLOMLinkSpeed
        Integer32,
    blade2InsLOMMAC
        DisplayString,
    blade2InsLOMLinkStatus
        INTEGER,
    blade2InsLOMPortDivide
        INTEGER,
    blade2InsLOMPortDivideNum
        Integer32
}

blade2HDDSlotTable    OBJECT-TYPE
    SYNTAX SEQUENCE OF blade2HDDSlotEntry
    MAX-ACCESS not-accessible
    STATUS     current
    DESCRIPTION "This shows the table of HDD slot of server blade2."
    ::= { blade2Install 7 }

blade2HDDSlotEntry    OBJECT-TYPE
    SYNTAX Blade2HDDSlotEntry
    MAX-ACCESS not-accessible
    STATUS    current
    DESCRIPTION "This shows the entry of HDD slot of server blade2."
    INDEX { blade2HDDSlotIndex }
    ::= { blade2HDDSlotTable 1 }

blade2HDDSlotIndex    OBJECT-TYPE
    SYNTAX    Integer32
    MAX-ACCESS    read-only
    STATUS    current
    DESCRIPTION    "This shows the index of HDD slot of server blade2."
    ::= { blade2HDDSlotEntry 1 }

blade2HDDSlotNum    OBJECT-TYPE
    SYNTAX    Integer32
    MAX-ACCESS    read-only
    STATUS    current
    DESCRIPTION    "This shows the number of HDD slots of server blade2."
    ::= { blade2HDDSlotEntry 2 }

blade2HDDSlotExist    OBJECT-TYPE
    SYNTAX    INTEGER {
    non-exist(1), exist(2), unknown(3)
    }
    MAX-ACCESS    read-only
    STATUS    current
    DESCRIPTION    "This shows the registrated state of HDD slot of server blade2."
    ::= { blade2HDDSlotEntry 3 }

blade2HDDSlotHDDType    OBJECT-TYPE
    SYNTAX    DisplayString 
    MAX-ACCESS    read-only
    STATUS    current
    DESCRIPTION    "This shows the HDD type of HDD slot of server blade2."
    ::= { blade2HDDSlotEntry 4 }

blade2HDDSlotHDDProductName    OBJECT-TYPE
    SYNTAX    DisplayString 
    MAX-ACCESS    read-only
    STATUS    current
    DESCRIPTION    "This shows the HDD product name of HDD slot of server blade2."
    ::= { blade2HDDSlotEntry 5 }

blade2HDDSlotHDDModel    OBJECT-TYPE
    SYNTAX    DisplayString 
    MAX-ACCESS    read-only
    STATUS    current
    DESCRIPTION    "This shows the HDD model of HDD slot of server blade2."
    ::= { blade2HDDSlotEntry 6 }

blade2HDDSlotHDDSerialNum    OBJECT-TYPE
    SYNTAX    DisplayString 
    MAX-ACCESS    read-only
    STATUS    current
    DESCRIPTION    "This shows the HDD serial number of HDD slot of server blade2."
    ::= { blade2HDDSlotEntry 7 }

blade2HDDSlotHDDCapacity    OBJECT-TYPE
    SYNTAX    Integer32
    UNITS    "GB"
    MAX-ACCESS    read-only
    STATUS    current
    DESCRIPTION    "This shows the HDD capacity of HDD slots of server blade2."
    ::= { blade2HDDSlotEntry 8 }

blade2HDDSlotHDDRPM    OBJECT-TYPE
    SYNTAX    Integer32
    UNITS    "rpm"
    MAX-ACCESS    read-only
    STATUS    current
    DESCRIPTION    "This shows the HDD drive speed of HDD slot of server blade2."
    ::= { blade2HDDSlotEntry 9 }

blade2HDDSlotHDDStatePower    OBJECT-TYPE
    SYNTAX    INTEGER {
    poweroff (1), poweron (2), unknown (3)
    }
    MAX-ACCESS    read-only
    STATUS    current
    DESCRIPTION    "This shows the HDD power supply state of HDD slot of server blade2."
    ::= { blade2HDDSlotEntry 10 }

blade2HDDSlotHDDStateHealth    OBJECT-TYPE
    SYNTAX    INTEGER {
    normal (1),fail (2),unknown (3),rebuild (4)
    }
    MAX-ACCESS    read-only
    STATUS    current
    DESCRIPTION    "This shows the HDD health state of HDD slot of server blade2."
    ::= { blade2HDDSlotEntry 11 }

blade2HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade2(activity)."
    ::= { blade2HDDSlotEntry 12 }

blade2HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade2(status)."
    ::= { blade2HDDSlotEntry 13 }

blade2HDDSlotHDDFWInfoName    OBJECT-TYPE
    SYNTAX    DisplayString 
    MAX-ACCESS    read-only
    STATUS    current
    DESCRIPTION    "This shows the HDD firmware name of HDD slot of server blade2."
    ::= { blade2HDDSlotEntry 20 }

blade2HDDSlotHDDFWInfoCurrentVer    OBJECT-TYPE
    SYNTAX    DisplayString 
    MAX-ACCESS    read-only
    STATUS    current
    DESCRIPTION    "This shows the HDD firmware current version of HDD slot of server blade2."
    ::= { blade2HDDSlotEntry 21 }

blade2HDDSlotHDDFWInfoNextVer    OBJECT-TYPE
    SYNTAX    DisplayString 
    MAX-ACCESS    read-only
    STATUS    current
    DESCRIPTION    "This shows the HDD firmware next version of HDD slot of server blade2."
    ::= { blade2HDDSlotEntry 22 }

Blade2HDDSlotEntry ::= SEQUENCE {
    blade2HDDSlotIndex
        Integer32,
    blade2HDDSlotNum
        Integer32,
    blade2HDDSlotExist
        INTEGER,
    blade2HDDSlotHDDType
        DisplayString,
    blade2HDDSlotHDDProductName
        DisplayString,
    blade2HDDSlotHDDModel
        DisplayString,
    blade2HDDSlotHDDSerialNum
        DisplayString,
    blade2HDDSlotHDDCapacity
        Integer32,
    blade2HDDSlotHDDRPM
        Integer32,
    blade2HDDSlotHDDStatePower
        INTEGER,
    blade2HDDSlotHDDStateHealth
        INTEGER,
    blade2HDDSlotHDDStateLEDACT
        INTEGER,
    blade2HDDSlotHDDStateLEDSTS
        INTEGER,
    blade2HDDSlotHDDFWInfoName
        DisplayString,
    blade2HDDSlotHDDFWInfoCurrentVer
        DisplayString,
    blade2HDDSlotHDDFWInfoNextVer
        DisplayString
}

blade2ExpansionHDDSlotTable    OBJECT-TYPE
    SYNTAX SEQUENCE OF blade2ExpansionHDDSlotEntry
    MAX-ACCESS not-accessible
    STATUS     current
    DESCRIPTION "This shows the table of expansion HDD slot of server blade2."
    ::= { blade2Install 8 }

blade2ExpansionHDDSlotEntry    OBJECT-TYPE
    SYNTAX Blade2ExpansionHDDSlotEntry
    MAX-ACCESS not-accessible
    STATUS    current
    DESCRIPTION "This shows the entry of expansion HDD slot of server blade2."
    INDEX { blade2ExpansionHDDSlotIndex }
    ::= { blade2ExpansionHDDSlotTable 1 }

blade2ExpansionHDDSlotIndex    OBJECT-TYPE
    SYNTAX    Integer32
    MAX-ACCESS    read-only
    STATUS    current
    DESCRIPTION    "This shows the index of expansion HDD slot of server blade2."
    ::= { blade2ExpansionHDDSlotEntry 1 }

blade2ExpansionHDDSlotNum    OBJECT-TYPE
    SYNTAX    Integer32
    MAX-ACCESS    read-only
    STATUS    current
    DESCRIPTION    "This shows the number of expansion HDD slots of server blade2."
    ::= { blade2ExpansionHDDSlotEntry 2 }

blade2ExpansionHDDSlotExist    OBJECT-TYPE
    SYNTAX    INTEGER {
    non-exist(1), exist(2), unknown(3)
    }
    MAX-ACCESS    read-only
    STATUS    current
    DESCRIPTION    "This shows the registrated state of expansion HDD slot of server blade2."
    ::= { blade2ExpansionHDDSlotEntry 3 }

blade2ExpansionHDDSlotHDDType    OBJECT-TYPE
    SYNTAX    DisplayString 
    MAX-ACCESS    read-only
    STATUS    current
    DESCRIPTION    "This shows the HDD type of expansion HDD slot of server blade2."
    ::= { blade2ExpansionHDDSlotEntry 4 }

blade2ExpansionHDDSlotHDDProductName    OBJECT-TYPE
    SYNTAX    DisplayString 
    MAX-ACCESS    read-only
    STATUS    current
    DESCRIPTION    "This shows the HDD product name of expansion HDD slot of server blade2."
    ::= { blade2ExpansionHDDSlotEntry 5 }

blade2ExpansionHDDSlotHDDModel    OBJECT-TYPE
    SYNTAX    DisplayString 
    MAX-ACCESS    read-only
    STATUS    current
    DESCRIPTION    "This shows the HDD model of expansion HDD slot of server blade2."
    ::= { blade2ExpansionHDDSlotEntry 6 }

blade2ExpansionHDDSlotHDDSerialNum    OBJECT-TYPE
    SYNTAX    DisplayString 
    MAX-ACCESS    read-only
    STATUS    current
    DESCRIPTION    "This shows the HDD serial number of expansion HDD slot of server blade2."
    ::= { blade2ExpansionHDDSlotEntry 7 }

blade2ExpansionHDDSlotHDDCapacity    OBJECT-TYPE
    SYNTAX    Integer32
    UNITS    "GB"
    MAX-ACCESS    read-only
    STATUS    current
    DESCRIPTION    "This shows the HDD capacity of expansion HDD slots of server blade2."
    ::= { blade2ExpansionHDDSlotEntry 8 }

blade2ExpansionHDDSlotHDDRPM    OBJECT-TYPE
    SYNTAX    Integer32
    UNITS    "rpm"
    MAX-ACCESS    read-only
    STATUS    current
    DESCRIPTION    "This shows the HDD drive speed of expansion HDD slot of server blade2."
    ::= { blade2ExpansionHDDSlotEntry 9 }

blade2ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade2."
    ::= { blade2ExpansionHDDSlotEntry 10 }

blade2ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade2."
    ::= { blade2ExpansionHDDSlotEntry 11 }

blade2ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade2(activity)."
    ::= { blade2ExpansionHDDSlotEntry 12 }

blade2ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade2(status)."
    ::= { blade2ExpansionHDDSlotEntry 13 }

blade2ExpansionHDDSlotHDDFWInfoName    OBJECT-TYPE
    SYNTAX    DisplayString 
    MAX-ACCESS    read-only
    STATUS    current
    DESCRIPTION    "This shows the HDD firmware name of expansion HDD slot of server blade2."
    ::= { blade2ExpansionHDDSlotEntry 20 }

blade2ExpansionHDDSlotHDDFWInfoCurrentVer    OBJECT-TYPE
    SYNTAX    DisplayString 
    MAX-ACCESS    read-only
    STATUS    current
    DESCRIPTION    "This shows the HDD firmware current version of expansion HDD slot of server blade2."
    ::= { blade2ExpansionHDDSlotEntry 21 }

blade2ExpansionHDDSlotHDDFWInfoNextVer    OBJECT-TYPE
    SYNTAX    DisplayString 
    MAX-ACCESS    read-only
    STATUS    current
    DESCRIPTION    "This shows the HDD firmware next version of expansion HDD slot of server blade2."
    ::= { blade2ExpansionHDDSlotEntry 22 }

Blade2ExpansionHDDSlotEntry ::= SEQUENCE {
    blade2ExpansionHDDSlotIndex
        Integer32,
    blade2ExpansionHDDSlotNum
        Integer32,
    blade2ExpansionHDDSlotExist
        INTEGER,
    blade2ExpansionHDDSlotHDDType
        DisplayString,
    blade2ExpansionHDDSlotHDDProductName
        DisplayString,
    blade2ExpansionHDDSlotHDDModel
        DisplayString,
    blade2ExpansionHDDSlotHDDSerialNum
        DisplayString,
    blade2ExpansionHDDSlotHDDCapacity
        Integer32,
    blade2ExpansionHDDSlotHDDRPM
        Integer32,
    blade2ExpansionHDDSlotHDDStatePower
        INTEGER,
    blade2ExpansionHDDSlotHDDStateHealth
        INTEGER,
    blade2ExpansionHDDSlotHDDStateLEDACT
        INTEGER,
    blade2ExpansionHDDSlotHDDStateLEDSTS
        INTEGER,
    blade2ExpansionHDDSlotHDDFWInfoName
        DisplayString,
    blade2ExpansionHDDSlotHDDFWInfoCurrentVer
        DisplayString,
    blade2ExpansionHDDSlotHDDFWInfoNextVer
        DisplayString
}

blade2VoltageSensorTable    OBJECT-TYPE
    SYNTAX SEQUENCE OF blade2VoltageSensorEntry
    MAX-ACCESS not-accessible
    STATUS     current
    DESCRIPTION "This shows the table of voltage sensor of server blade2."
    ::= { blade2State 40 }

blade2VoltageSensorEntry    OBJECT-TYPE
    SYNTAX Blade2VoltageSensorEntry
    MAX-ACCESS not-accessible
    STATUS    current
    DESCRIPTION "This shows the entry of voltage sensor of server blade2."
    INDEX { blade2VoltageSensorIndex }
    ::= { blade2VoltageSensorTable 1 }

blade2VoltageSensorIndex    OBJECT-TYPE
    SYNTAX    Integer32
    MAX-ACCESS    read-only
    STATUS    current
    DESCRIPTION    "This shows the index of voltage sensor of server blade2."
    ::= { blade2VoltageSensorEntry 1 }

blade2VoltageSensorName    OBJECT-TYPE
    SYNTAX    DisplayString 
    MAX-ACCESS    read-only
    STATUS    current
    DESCRIPTION    "This shows the voltage sensor name of server blade2."
    ::= { blade2VoltageSensorEntry 2 }

blade2VoltageSensorValue    OBJECT-TYPE
    SYNTAX    Integer32
    UNITS    "0.1 V"
    MAX-ACCESS    read-only
    STATUS    current
    DESCRIPTION    "This shows the voltage sensor value of server blade2."
    ::= { blade2VoltageSensorEntry 3 }

blade2VoltageSensorValid    OBJECT-TYPE
    SYNTAX    INTEGER {
    invalid (1),valid (2),unknown (3)
    }
    MAX-ACCESS    read-only
    STATUS    current
    DESCRIPTION    "This shows the validity of voltage sensor value of server blade2."
    ::= { blade2VoltageSensorEntry 4 }

Blade2VoltageSensorEntry ::= SEQUENCE {
    blade2VoltageSensorIndex
        Integer32,
    blade2VoltageSensorName
        DisplayString,
    blade2VoltageSensorValue
        Integer32,
    blade2VoltageSensorValid
        INTEGER
}

blade2TempSensorTable    OBJECT-TYPE
    SYNTAX SEQUENCE OF blade2TempSensorEntry
    MAX-ACCESS not-accessible
    STATUS     current
    DESCRIPTION "This shows the table of temperature sensor of server blade2."
    ::= { blade2State 41 }

blade2TempSensorEntry    OBJECT-TYPE
    SYNTAX Blade2TempSensorEntry
    MAX-ACCESS not-accessible
    STATUS    current
    DESCRIPTION "This shows the entry of temperature sensor of server blade2."
    INDEX { blade2TempSensorIndex }
    ::= { blade2TempSensorTable 1 }

blade2TempSensorIndex    OBJECT-TYPE
    SYNTAX    Integer32
    MAX-ACCESS    read-only
    STATUS    current
    DESCRIPTION    "This shows the index of temperature sensor of server blade2."
    ::= { blade2TempSensorEntry 1 }

blade2TempSensorName    OBJECT-TYPE
    SYNTAX    DisplayString 
    MAX-ACCESS    read-only
    STATUS    current
    DESCRIPTION    "This shows the temperature sensor name of server blade2."
    ::= { blade2TempSensorEntry 2 }

blade2TempSensorValue    OBJECT-TYPE
    SYNTAX    Integer32
    UNITS    "0.1 degrees C"
    MAX-ACCESS    read-only
    STATUS    current
    DESCRIPTION    "This shows the temperature sensor value of server blade2."
    ::= { blade2TempSensorEntry 3 }

blade2TempSensorValid    OBJECT-TYPE
    SYNTAX    INTEGER {
    invalid (1),valid (2),unknown (3)
    }
    MAX-ACCESS    read-only
    STATUS    current
    DESCRIPTION    "This shows the validity of temperature sensor value of server blade2."
    ::= { blade2TempSensorEntry 4 }

Blade2TempSensorEntry ::= SEQUENCE {
    blade2TempSensorIndex
        Integer32,
    blade2TempSensorName
        DisplayString,
    blade2TempSensorValue
        Integer32,
    blade2TempSensorValid
        INTEGER
}

blade2FWInfo    OBJECT IDENTIFIER ::= { blade2 5 } 

blade2FWInfoTotalCurrentVer    OBJECT-TYPE
    SYNTAX    DisplayString (SIZE(0..40))
    MAX-ACCESS    read-only
    STATUS    current
    DESCRIPTION    "This shows the total current version of firmware of server blade2."
    ::= { blade2FWInfo 1 }

blade2FWInfoTotalNextVer    OBJECT-TYPE
    SYNTAX    DisplayString (SIZE(0..40))
    MAX-ACCESS    read-only
    STATUS    current
    DESCRIPTION    "This shows the total next version of firmware of server blade2."
    ::= { blade2FWInfo 2 }

blade2FWInfoTable    OBJECT-TYPE
    SYNTAX SEQUENCE OF blade2FWInfoEntry
    MAX-ACCESS not-accessible
    STATUS     current
    DESCRIPTION "This shows the table of firmware information of server blade2."
    ::= { blade2FWInfo 3 }

blade2FWInfoEntry    OBJECT-TYPE
    SYNTAX Blade2FWInfoEntry
    MAX-ACCESS not-accessible
    STATUS    current
    DESCRIPTION "This shows the entry of firmware information of server blade2."
    INDEX { blade2FWInfoIndex }
    ::= { blade2FWInfoTable 1 }

blade2FWInfoIndex    OBJECT-TYPE
    SYNTAX    Integer32
    MAX-ACCESS    read-only
    STATUS    current
    DESCRIPTION    "This shows the index of firmware information of server blade2."
    ::= { blade2FWInfoEntry 1 }

blade2FWInfoName    OBJECT-TYPE
    SYNTAX    DisplayString (SIZE(0..40))
    MAX-ACCESS    read-only
    STATUS    current
    DESCRIPTION    "This shows the firmware name of server blade2."
    ::= { blade2FWInfoEntry 2 }

blade2FWCurrentVer    OBJECT-TYPE
    SYNTAX    DisplayString (SIZE(0..40))
    MAX-ACCESS    read-only
    STATUS    current
    DESCRIPTION    "This shows the firmware current version of server blade2."
    ::= { blade2FWInfoEntry 3 }

blade2FWInfoNextVer    OBJECT-TYPE
    SYNTAX    DisplayString (SIZE(0..40))
    MAX-ACCESS    read-only
    STATUS    current
    DESCRIPTION    "This shows the firmware next version of server blade2."
    ::= { blade2FWInfoEntry 4 }

blade2FWInfoHVMCurrentVer    OBJECT-TYPE
    SYNTAX    DisplayString (SIZE(0..40))
    MAX-ACCESS    read-only
    STATUS    current
    DESCRIPTION    "This shows the HVM current version of server blade2."
    ::= { blade2FWInfo 4 }

blade2FWInfoHVMNextVer    OBJECT-TYPE
    SYNTAX    DisplayString (SIZE(0..40))
    MAX-ACCESS    read-only
    STATUS    current
    DESCRIPTION    "This shows the HVM next version of server blade2."
    ::= { blade2FWInfo 5 }

Blade2FWInfoEntry ::= SEQUENCE {
    blade2FWInfoIndex
        Integer32,
    blade2FWInfoName
        DisplayString,
    blade2FWCurrentVer
        DisplayString,
    blade2FWInfoNextVer
        DisplayString,
    blade2FWInfoHVMCurrentVer
        DisplayString,
    blade2FWInfoHVMNextVer
        DisplayString
}

blade3    OBJECT IDENTIFIER ::= { blade 3 } 

blade3BasicInfo    OBJECT IDENTIFIER ::= { blade3 1 } 

blade3InfoProductName    OBJECT-TYPE
    SYNTAX    DisplayString (SIZE(0..40))
    MAX-ACCESS    read-only
    STATUS    current
    DESCRIPTION    "This shows the product name of server blade3."
    ::= { blade3BasicInfo 1 }

blade3InfoModel    OBJECT-TYPE
    SYNTAX    DisplayString (SIZE(0..40))
    MAX-ACCESS    read-only
    STATUS    current
    DESCRIPTION    "This shows the model name of server blade3."
    ::= { blade3BasicInfo 2 }

blade3InfoSerialNum    OBJECT-TYPE
    SYNTAX    DisplayString (SIZE(0..40))
    MAX-ACCESS    read-only
    STATUS    current
    DESCRIPTION    "This shows the serial number of server blade3."
    ::= { blade3BasicInfo 3 }

blade3InfoProductVersion    OBJECT-TYPE
    SYNTAX    DisplayString (SIZE(0..40))
    MAX-ACCESS    read-only
    STATUS    current
    DESCRIPTION    "This shows the product version of server blade3."
    ::= { blade3BasicInfo 4 }

blade3InfoProductManufacturer    OBJECT-TYPE
    SYNTAX    DisplayString (SIZE(0..40))
    MAX-ACCESS    read-only
    STATUS    current
    DESCRIPTION    "This shows the product manufacturer of server blade3."
    ::= { blade3BasicInfo 5 }

blade3InfoBoardProductName    OBJECT-TYPE
    SYNTAX    DisplayString (SIZE(0..40))
    MAX-ACCESS    read-only
    STATUS    current
    DESCRIPTION    "This shows the board product name of server blade3."
    ::= { blade3BasicInfo 7 }

blade3InfoBoardSerialNum    OBJECT-TYPE
    SYNTAX    DisplayString (SIZE(0..40))
    MAX-ACCESS    read-only
    STATUS    current
    DESCRIPTION    "This shows the board serial number of server blade3."
    ::= { blade3BasicInfo 8 }

blade3InfoBoardManufacturer    OBJECT-TYPE
    SYNTAX    DisplayString (SIZE(0..40))
    MAX-ACCESS    read-only
    STATUS    current
    DESCRIPTION    "This shows the board manufacturer of server blade3."
    ::= { blade3BasicInfo 9 }

blade3InfoUUID    OBJECT-TYPE
    SYNTAX    DisplayString (SIZE(0..40))
    MAX-ACCESS    read-only
    STATUS    current
    DESCRIPTION    "This shows UUID(universal Unique ID) of server blade3."
    ::= { blade3BasicInfo 10 }

blade3InfoLogicalPartitionSupport    OBJECT-TYPE
    SYNTAX    INTEGER {
    not-support(1), support(2),unknown(3)
    }
    MAX-ACCESS    read-only
    STATUS    current
    DESCRIPTION    "This shows whether the server blade3 supports HVM or not of server blade1."
    ::= { blade3BasicInfo 11 }

blade3InfoRemoteKVMSupport    OBJECT-TYPE
    SYNTAX    INTEGER {
    not-support(1), support(2),unknown(3)
    }
    MAX-ACCESS    read-only
    STATUS    current
    DESCRIPTION    "This shows whether the server blade3 supports remote KVM or not of server blade1."
    ::= { blade3BasicInfo 12 }

blade3InfoSpec    OBJECT IDENTIFIER ::= { blade3BasicInfo 20 } 

blade3SpecInputCurrentType    OBJECT-TYPE
    SYNTAX    INTEGER {
    ac(1),dc(2),unknown(3)
    }
    MAX-ACCESS    read-only
    STATUS    current
    DESCRIPTION    "This shows the currency type of server blade3."
    ::= { blade3InfoSpec 1 }

blade3SpecRateVoltage    OBJECT-TYPE
    SYNTAX    Integer32
    UNITS    "0.1 V"
    MAX-ACCESS    read-only
    STATUS    current
    DESCRIPTION    "This shows the rated voltage of server blade3."
    ::= { blade3InfoSpec 2 }

blade3SpecConsumptionCurrent    OBJECT-TYPE
    SYNTAX    Integer32
    UNITS    "0.1 A"
    MAX-ACCESS    read-only
    STATUS    current
    DESCRIPTION    "This shows the consumption current of server blade3."
    ::= { blade3InfoSpec 3 }

blade3SpecPowerConsumption    OBJECT-TYPE
    SYNTAX    Integer32
    UNITS    "W"
    MAX-ACCESS    read-only
    STATUS    current
    DESCRIPTION    "This shows the power consumption of server blade3."
    ::= { blade3InfoSpec 4 }

blade3SpecMass    OBJECT-TYPE
    SYNTAX    Integer32
    UNITS    "0.1 kg"
    MAX-ACCESS    read-only
    STATUS    current
    DESCRIPTION    "This shows the weight of server blade3."
    ::= { blade3InfoSpec 5 }

blade3InfoUpperLimitIntakeTemp    OBJECT-TYPE
    SYNTAX    Integer32
    UNITS    "0.1 degrees C"
    MAX-ACCESS    read-only
    STATUS    current
    DESCRIPTION    "This shows the maximum limited intake temperature of server blade3."
    ::= { blade3InfoSpec 6 }

blade3InfoLowerLimitIntakeTemp    OBJECT-TYPE
    SYNTAX    Integer32
    UNITS    "0.1 degrees C"
    MAX-ACCESS    read-only
    STATUS    current
    DESCRIPTION    "This shows the minimum limited intake temperature of server blade3."
    ::= { blade3InfoSpec 7 }

blade3SpecSize    OBJECT-TYPE
    SYNTAX    DisplayString (SIZE(0..40))
    MAX-ACCESS    read-only
    STATUS    current
    DESCRIPTION    "This shows the size of server blade3."
    ::= { blade3InfoSpec 8 }

blade3SpecOccupySlots    OBJECT-TYPE
    SYNTAX    Integer32
    MAX-ACCESS    read-only
    STATUS    current
    DESCRIPTION    "This shows the dedicated number of slots of server blade3."
    ::= { blade3InfoSpec 9 }

blade3SpecExpansionBladeSlot    OBJECT-TYPE
    SYNTAX    Integer32
    MAX-ACCESS    read-only
    STATUS    current
    DESCRIPTION    "This shows the number of slots of expansion blade of server blade3."
    ::= { blade3InfoSpec 10 }

blade3InfoExpansionBladeTable    OBJECT-TYPE
    SYNTAX SEQUENCE OF blade3InfoExpansionBladeEntry
    MAX-ACCESS not-accessible
    STATUS     current
    DESCRIPTION "This shows the table of expansion blade slot of server blade3."
    ::= { blade3BasicInfo 30 }

blade3InfoExpansionBladeEntry    OBJECT-TYPE
    SYNTAX Blade3InfoExpansionBladeEntry
    MAX-ACCESS not-accessible
    STATUS    current
    DESCRIPTION "This shows the entry of expansion blade slot of server blade3."
    INDEX { blade3InfoExpansionBladeIndex }
    ::= { blade3InfoExpansionBladeTable 1 }

blade3InfoExpansionBladeIndex    OBJECT-TYPE
    SYNTAX    Integer32
    MAX-ACCESS    read-only
    STATUS    current
    DESCRIPTION    "This shows the index of expansion blade slot of server blade3."
    ::= { blade3InfoExpansionBladeEntry 1 }

blade3InfoExpansionBladeExist    OBJECT-TYPE
    SYNTAX    INTEGER {
    non-exist(1), exist(2), unknown(3)
    }
    MAX-ACCESS    read-only
    STATUS    current
    DESCRIPTION    "This shows the registrated state of expansion blade of server blade3."
    ::= { blade3InfoExpansionBladeEntry 2 }

blade3InfoExpansionBladeProductName    OBJECT-TYPE
    SYNTAX    DisplayString (SIZE(0..40))
    MAX-ACCESS    read-only
    STATUS    current
    DESCRIPTION    "This shows the product name of expansion blade of server blade3."
    ::= { blade3InfoExpansionBladeEntry 3 }

blade3InfoExpansionBladeModel    OBJECT-TYPE
    SYNTAX    DisplayString (SIZE(0..40))
    MAX-ACCESS    read-only
    STATUS    current
    DESCRIPTION    "This shows the model name of expansion blade of server blade3."
    ::= { blade3InfoExpansionBladeEntry 4 }

blade3InfoExpansionBladeSerialNum    OBJECT-TYPE
    SYNTAX    DisplayString (SIZE(0..40))
    MAX-ACCESS    read-only
    STATUS    current
    DESCRIPTION    "This shows the serial number of expansion blade of server blade3."
    ::= { blade3InfoExpansionBladeEntry 5 }

blade3InfoExpansionBladeProductVersion    OBJECT-TYPE
    SYNTAX    DisplayString (SIZE(0..40))
    MAX-ACCESS    read-only
    STATUS    current
    DESCRIPTION    "This shows the product version of expansion blade of server blade3."
    ::= { blade3InfoExpansionBladeEntry 6 }

blade3InfoExpansionBladeProductManufacturer    OBJECT-TYPE
    SYNTAX    DisplayString (SIZE(0..40))
    MAX-ACCESS    read-only
    STATUS    current
    DESCRIPTION    "This shows the product manufacturer of expansion blade of server blade3."
    ::= { blade3InfoExpansionBladeEntry 7 }

blade3InfoExpansionBladeBoardProductName    OBJECT-TYPE
    SYNTAX    DisplayString (SIZE(0..40))
    MAX-ACCESS    read-only
    STATUS    current
    DESCRIPTION    "This shows the board product name of expansion blade of server blade3."
    ::= { blade3InfoExpansionBladeEntry 9 }

blade3InfoExpansionBladeBoardSerialNum    OBJECT-TYPE
    SYNTAX    DisplayString (SIZE(0..40))
    MAX-ACCESS    read-only
    STATUS    current
    DESCRIPTION    "This shows the board serial number of expansion blade of server blade3."
    ::= { blade3InfoExpansionBladeEntry 10 }

blade3InfoExpansionBladeBoardManufacturer    OBJECT-TYPE
    SYNTAX    DisplayString (SIZE(0..40))
    MAX-ACCESS    read-only
    STATUS    current
    DESCRIPTION    "This shows the board manufacturer of expansion blade of server blade3."
    ::= { blade3InfoExpansionBladeEntry 11 }

Blade3InfoExpansionBladeEntry ::= SEQUENCE {
    blade3InfoExpansionBladeIndex
        Integer32,
    blade3InfoExpansionBladeExist
        INTEGER,
    blade3InfoExpansionBladeProductName
        DisplayString,
    blade3InfoExpansionBladeModel
        DisplayString,
    blade3InfoExpansionBladeSerialNum
        DisplayString,
    blade3InfoExpansionBladeProductVersion
        DisplayString,
    blade3InfoExpansionBladeProductManufacturer
        DisplayString,
    blade3InfoExpansionBladeBoardProductName
        DisplayString,
    blade3InfoExpansionBladeBoardSerialNum
        DisplayString,
    blade3InfoExpansionBladeBoardManufacturer
        DisplayString
}

blade3Capacity    OBJECT IDENTIFIER ::= { blade3 2 } 

blade3CapacityCPUSocket    OBJECT-TYPE
    SYNTAX    Integer32
    MAX-ACCESS    read-only
    STATUS    current
    DESCRIPTION    "This shows the capacity of CPU sockets of server blade3."
    ::= { blade3Capacity 1 }

blade3CapacityDIMMSlot    OBJECT-TYPE
    SYNTAX    Integer32
    MAX-ACCESS    read-only
    STATUS    current
    DESCRIPTION    "This shows the capacity of DIMM slots of server blade3."
    ::= { blade3Capacity 2 }

blade3CapacityPCISlot    OBJECT-TYPE
    SYNTAX    Integer32
    MAX-ACCESS    read-only
    STATUS    current
    DESCRIPTION    "This shows the capacity of PCI slots of server blade3."
    ::= { blade3Capacity 3 }

blade3CapacityLOM    OBJECT-TYPE
    SYNTAX    Integer32
    MAX-ACCESS    read-only
    STATUS    current
    DESCRIPTION    "This shows the capacity of onboard LAN ports of server blade3."
    ::= { blade3Capacity 4 }

blade3CapacityFan    OBJECT-TYPE
    SYNTAX    Integer32
    MAX-ACCESS    read-only
    STATUS    current
    DESCRIPTION    "This shows the capacity of onboard fans of server blade3."
    ::= { blade3Capacity 5 }

blade3CapacityHDDSlot    OBJECT-TYPE
    SYNTAX    Integer32
    MAX-ACCESS    read-only
    STATUS    current
    DESCRIPTION    "This shows the capacity of HDD slots of server blade3."
    ::= { blade3Capacity 6 }

blade3CapacityVoltageSensor    OBJECT-TYPE
    SYNTAX    Integer32
    MAX-ACCESS    read-only
    STATUS    current
    DESCRIPTION    "This shows the capacity of voltage sensors of blade3."
    ::= { blade3Capacity 7 }

blade3CapacityTempSensor    OBJECT-TYPE
    SYNTAX    Integer32
    MAX-ACCESS    read-only
    STATUS    current
    DESCRIPTION    "This shows the capacity of temperature sensors of blade3."
    ::= { blade3Capacity 8 }

blade3CapacityExpansionHDDSlot    OBJECT-TYPE
    SYNTAX    Integer32
    MAX-ACCESS    read-only
    STATUS    current
    DESCRIPTION    "This shows the capacity of expansion HDD slots of server blade3."
    ::= { blade3Capacity 9 }

blade3CapacityLED    OBJECT-TYPE
    SYNTAX    Integer32
    MAX-ACCESS    read-only
    STATUS    current
    DESCRIPTION    "This shows the capacity of count of LEDs of server blade3."
    ::= { blade3Capacity 10 }

blade3Settings    OBJECT IDENTIFIER ::= { blade3 3 } 

blade3SettingsBelongPartitionNum    OBJECT-TYPE
    SYNTAX    Integer32
    MAX-ACCESS    read-only
    STATUS    current
    DESCRIPTION    "This shows the partition number of server blade3."
    ::= { blade3Settings 1 }

blade3SettingsDetailHVMLicenceModel    OBJECT-TYPE
    SYNTAX    DisplayString (SIZE(0..40))
    MAX-ACCESS    read-only
    STATUS    current
    DESCRIPTION    "This shows the HVM licence of detailed server blade3 (model). "
    ::= { blade3Settings 2 }

blade3SettingsDetailHVMLicenceAvailableVersion    OBJECT-TYPE
    SYNTAX    DisplayString (SIZE(0..40))
    MAX-ACCESS    read-only
    STATUS    current
    DESCRIPTION    "This shows the HVM licence of detailed server blade3 (available version). "
    ::= { blade3Settings 3 }

blade3SettingsManagementPortIPAddress    OBJECT-TYPE
    SYNTAX    DisplayString (SIZE(0..40))
    MAX-ACCESS    read-only
    STATUS    current
    DESCRIPTION    "This shows the IP address of management port of server blade3."
    ::= { blade3Settings 4 }

blade3State    OBJECT IDENTIFIER ::= { blade3 4 } 

blade3StateSlotNum    OBJECT-TYPE
    SYNTAX    Integer32
    MAX-ACCESS    read-only
    STATUS    current
    DESCRIPTION    "This shows the number of installed slots of server blade3."
    ::= { blade3State 1 }

blade3StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade3."
    ::= { blade3State 2 }

blade3StateHealth    OBJECT-TYPE
    SYNTAX    INTEGER {
    normal (1),fail (2),unknown (3)
    }
    MAX-ACCESS    read-only
    STATUS    current
    DESCRIPTION    "This shows the health state of server blade3."
    ::= { blade3State 3 }

blade3StatePrimaly    OBJECT-TYPE
    SYNTAX    INTEGER {
    primary(1), non-primary(2),unknown(3)
    }
    MAX-ACCESS    read-only
    STATUS    current
    DESCRIPTION    "This shows the primary state of server blade3."
    ::= { blade3State 4 }

blade3StateCurrentVoltage    OBJECT-TYPE
    SYNTAX    Integer32
    UNITS    "0.1 V"
    MAX-ACCESS    read-only
    STATUS    current
    DESCRIPTION    "This shows the current voltage of server blade3."
    ::= { blade3State 5 }

blade3StateConsumptionCurrent    OBJECT-TYPE
    SYNTAX    Integer32
    UNITS    "0.1 A"
    MAX-ACCESS    read-only
    STATUS    current
    DESCRIPTION    "This shows the consumption current of server blade3."
    ::= { blade3State 6 }

blade3StatePowerConsumption    OBJECT-TYPE
    SYNTAX    Integer32
    UNITS    "W"
    MAX-ACCESS    read-only
    STATUS    current
    DESCRIPTION    "This shows the power consumption of server blade3."
    ::= { blade3State 7 }

blade3StateIntakeTemp    OBJECT-TYPE
    SYNTAX    INTEGER {
    normal (1), higher-warning (2), higher-error (3), lower-warning (4), unknown(5)
    }
    MAX-ACCESS    read-only
    STATUS    current
    DESCRIPTION    "This shows the state of intake temperature of server blade3."
    ::= { blade3State 8 }

blade3StateLEDTable    OBJECT-TYPE
    SYNTAX SEQUENCE OF blade3StateLEDEntry
    MAX-ACCESS not-accessible
    STATUS     current
    DESCRIPTION "This shows the table of LED of server blade3."
    ::= { blade3State 9 }

blade3StateLEDEntry    OBJECT-TYPE
    SYNTAX Blade3StateLEDEntry
    MAX-ACCESS not-accessible
    STATUS    current
    DESCRIPTION "This shows the entry of LED of server blade3."
    INDEX { blade3StateLEDIndex }
    ::= { blade3StateLEDTable 1 }

blade3StateLEDIndex    OBJECT-TYPE
    SYNTAX    Integer32
    MAX-ACCESS    read-only
    STATUS    current
    DESCRIPTION    "This shows the index of LED of server blade3."
    ::= { blade3StateLEDEntry 1 }

blade3StateLEDName    OBJECT-TYPE
    SYNTAX    DisplayString (SIZE(0..40))
    MAX-ACCESS    read-only
    STATUS    current
    DESCRIPTION    "This shows the name of LED of server blade3."
    ::= { blade3StateLEDEntry 2 }

blade3StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade3."
    ::= { blade3StateLEDEntry 3 }

blade3StateLEDColor    OBJECT-TYPE
    SYNTAX    INTEGER {
    blue (1),green (2),red (3),amber (4),unknown (5)
    }
    MAX-ACCESS    read-only
    STATUS    current
    DESCRIPTION    "This shows the color of LED of server blade3."
    ::= { blade3StateLEDEntry 4 }

Blade3StateLEDEntry ::= SEQUENCE {
    blade3StateLEDIndex
        Integer32,
    blade3StateLEDName
        DisplayString,
    blade3StateLEDState
        INTEGER,
    blade3StateLEDColor
        INTEGER
}

blade3StateOther    OBJECT IDENTIFIER ::= { blade3State 20 } 

blade3MaintMode    OBJECT-TYPE
    SYNTAX    INTEGER {
    Normal(1), CE-Maint-mode(2), User-Maint-mode(3), unknown(4)
    }
    MAX-ACCESS    read-only
    STATUS    current
    DESCRIPTION    "This shows the maintenance mode of server blade3."
    ::= { blade3StateOther 1 }

blade3Install    OBJECT IDENTIFIER ::= { blade3State 30 } 

blade3InsCPUSocketTable    OBJECT-TYPE
    SYNTAX SEQUENCE OF blade3InsCPUSocketEntry
    MAX-ACCESS not-accessible
    STATUS     current
    DESCRIPTION "This shows the table of CPU socket of server blade3."
    ::= { blade3Install 1 }

blade3InsCPUSocketEntry    OBJECT-TYPE
    SYNTAX Blade3InsCPUSocketEntry
    MAX-ACCESS not-accessible
    STATUS    current
    DESCRIPTION "This shows the entry of CPU socket of server blade3."
    INDEX { blade3InsCPUSocketIndex }
    ::= { blade3InsCPUSocketTable 1 }

blade3InsCPUSocketIndex    OBJECT-TYPE
    SYNTAX    Integer32
    MAX-ACCESS    read-only
    STATUS    current
    DESCRIPTION    "This shows the index of CPU socket of server blade3."
    ::= { blade3InsCPUSocketEntry 1 }

blade3InsCPUSocketNum    OBJECT-TYPE
    SYNTAX    Integer32
    MAX-ACCESS    read-only
    STATUS    current
    DESCRIPTION    "This shows the number of CPU sockets of server blade3."
    ::= { blade3InsCPUSocketEntry 2 }

blade3InsCPUSocketExist    OBJECT-TYPE
    SYNTAX    INTEGER {
    non-exist(1), exist(2), unknown(3)
    }
    MAX-ACCESS    read-only
    STATUS    current
    DESCRIPTION    "This shows the registrated state of CPU socket of server blade3."
    ::= { blade3InsCPUSocketEntry 3 }

blade3InsCPUSocketCPUName    OBJECT-TYPE
    SYNTAX    DisplayString (SIZE(0..40))
    MAX-ACCESS    read-only
    STATUS    current
    DESCRIPTION    "This shows the CPU name of CPU socket of server blade3."
    ::= { blade3InsCPUSocketEntry 4 }

blade3InsCPUSocketCPUFrequency    OBJECT-TYPE
    SYNTAX    Integer32
    UNITS    "MHz"
    MAX-ACCESS    read-only
    STATUS    current
    DESCRIPTION    "This shows the CPU frequency of CPU socket of server blade3."
    ::= { blade3InsCPUSocketEntry 5 }

blade3InsCPUSocketCPUStepping    OBJECT-TYPE
    SYNTAX    DisplayString 
    MAX-ACCESS    read-only
    STATUS    current
    DESCRIPTION    "This shows the CPU stepping of CPU socket of server blade3."
    ::= { blade3InsCPUSocketEntry 6 }

blade3InsCPUSocketCPUCoreNum    OBJECT-TYPE
    SYNTAX    Integer32
    MAX-ACCESS    read-only
    STATUS    current
    DESCRIPTION    "This shows the CPU core number of CPU socket of server blade3."
    ::= { blade3InsCPUSocketEntry 7 }

blade3InsCPUSocketCPUUpperLimitTemp    OBJECT-TYPE
    SYNTAX    Integer32
    UNITS    "0.1 degrees C"
    MAX-ACCESS    read-only
    STATUS    current
    DESCRIPTION    "This shows the maximum limited CPU temperature of server blade3."
    ::= { blade3InsCPUSocketEntry 8 }

blade3InsCPUSocketCPULowerLimitTemp    OBJECT-TYPE
    SYNTAX    Integer32
    UNITS    "0.1 degrees C"
    MAX-ACCESS    read-only
    STATUS    current
    DESCRIPTION    "This shows the minimum limited CPU temperature of server blade3."
    ::= { blade3InsCPUSocketEntry 9 }

blade3InsDIMMCapacity    OBJECT-TYPE
    SYNTAX    Integer32
    UNITS    "GB"
    MAX-ACCESS    read-only
    STATUS    current
    DESCRIPTION    "This shows the total amount of DIMM capacity of server blade3."
    ::= { blade3Install 2 }

Blade3InsCPUSocketEntry ::= SEQUENCE {
    blade3InsCPUSocketIndex
        Integer32,
    blade3InsCPUSocketNum
        Integer32,
    blade3InsCPUSocketExist
        INTEGER,
    blade3InsCPUSocketCPUName
        DisplayString,
    blade3InsCPUSocketCPUFrequency
        Integer32,
    blade3InsCPUSocketCPUStepping
        DisplayString,
    blade3InsCPUSocketCPUCoreNum
        Integer32,
    blade3InsCPUSocketCPUUpperLimitTemp
        Integer32,
    blade3InsCPUSocketCPULowerLimitTemp
        Integer32,
    blade3InsDIMMCapacity
        Integer32
}

blade3InsDIMMSlotTable    OBJECT-TYPE
    SYNTAX SEQUENCE OF blade3InsDIMMSlotEntry
    MAX-ACCESS not-accessible
    STATUS     current
    DESCRIPTION "This shows the table of DIMM slot of server blade3."
    ::= { blade3Install 3 }

blade3InsDIMMSlotEntry    OBJECT-TYPE
    SYNTAX Blade3InsDIMMSlotEntry
    MAX-ACCESS not-accessible
    STATUS    current
    DESCRIPTION "This shows the entry of DIMM slot of server blade3."
    INDEX { blade3InsDIMMSlotIndex }
    ::= { blade3InsDIMMSlotTable 1 }

blade3InsDIMMSlotIndex    OBJECT-TYPE
    SYNTAX    Integer32
    MAX-ACCESS    read-only
    STATUS    current
    DESCRIPTION    "This shows the index of DIMM slot of server blade3."
    ::= { blade3InsDIMMSlotEntry 1 }

blade3InsDIMMSlotExist    OBJECT-TYPE
    SYNTAX    INTEGER {
    non-exist(1), exist(2), unknown(3)
    }
    MAX-ACCESS    read-only
    STATUS    current
    DESCRIPTION    "This shows the registrated state of DIMM slot of server blade3."
    ::= { blade3InsDIMMSlotEntry 2 }

blade3InsDIMMSlotDIMMCapacity    OBJECT-TYPE
    SYNTAX    Integer32
    UNITS    "GB"
    MAX-ACCESS    read-only
    STATUS    current
    DESCRIPTION    "This shows the capacity of DIMM slots of server blade3."
    ::= { blade3InsDIMMSlotEntry 3 }

blade3InsDIMMSlotDIMMType    OBJECT-TYPE
    SYNTAX    DisplayString 
    MAX-ACCESS    read-only
    STATUS    current
    DESCRIPTION    "This shows the DIMM type of DIMM slot of server blade3."
    ::= { blade3InsDIMMSlotEntry 4 }

blade3InsDIMMSlotDIMMFrequency    OBJECT-TYPE
    SYNTAX    Integer32
    UNITS    "MHz"
    MAX-ACCESS    read-only
    STATUS    current
    DESCRIPTION    "This shows the DIMM frequency of DIMM slot of server blade3."
    ::= { blade3InsDIMMSlotEntry 5 }

blade3InsDIMMSlotDIMMCasLatency    OBJECT-TYPE
    SYNTAX    Integer32
    MAX-ACCESS    read-only
    STATUS    current
    DESCRIPTION    "This shows the DIMM cas latency of DIMM slot of server blade3."
    ::= { blade3InsDIMMSlotEntry 6 }

blade3InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade3."
    ::= { blade3InsDIMMSlotEntry 7 }

Blade3InsDIMMSlotEntry ::= SEQUENCE {
    blade3InsDIMMSlotIndex
        Integer32,
    blade3InsDIMMSlotExist
        INTEGER,
    blade3InsDIMMSlotDIMMCapacity
        Integer32,
    blade3InsDIMMSlotDIMMType
        DisplayString,
    blade3InsDIMMSlotDIMMFrequency
        Integer32,
    blade3InsDIMMSlotDIMMCasLatency
        Integer32,
    blade3InsDIMMSlotDIMMStatus
        INTEGER
}

blade3InsPCISlotTable    OBJECT-TYPE
    SYNTAX SEQUENCE OF blade3InsPCISlotEntry
    MAX-ACCESS not-accessible
    STATUS     current
    DESCRIPTION "This shows the table of PCI slot of server blade3."
    ::= { blade3Install 4 }

blade3InsPCISlotEntry    OBJECT-TYPE
    SYNTAX Blade3InsPCISlotEntry
    MAX-ACCESS not-accessible
    STATUS    current
    DESCRIPTION "This shows the entry of PCI slot of server blade3."
    INDEX { blade3InsPCISlotIndex }
    ::= { blade3InsPCISlotTable 1 }

blade3InsPCISlotIndex    OBJECT-TYPE
    SYNTAX    Integer32
    MAX-ACCESS    read-only
    STATUS    current
    DESCRIPTION    "This shows the index of PCI slot of server blade3."
    ::= { blade3InsPCISlotEntry 1 }

blade3InsPCISlotType    OBJECT-TYPE
    SYNTAX    DisplayString 
    MAX-ACCESS    read-only
    STATUS    current
    DESCRIPTION    "This shows the type of PCI slot of server blade3."
    ::= { blade3InsPCISlotEntry 2 }

blade3InsPCISlotExist    OBJECT-TYPE
    SYNTAX    INTEGER {
    non-exist(1), exist(2), unknown(3)
    }
    MAX-ACCESS    read-only
    STATUS    current
    DESCRIPTION    "This shows the registrated state of PCI slot of server blade3."
    ::= { blade3InsPCISlotEntry 3 }

blade3InsPCISlotPCIType    OBJECT-TYPE
    SYNTAX    DisplayString 
    MAX-ACCESS    read-only
    STATUS    current
    DESCRIPTION    "This shows the PCI type of PCI slot of server blade3."
    ::= { blade3InsPCISlotEntry 4 }

blade3InsPCISlotPCIProductName    OBJECT-TYPE
    SYNTAX    DisplayString 
    MAX-ACCESS    read-only
    STATUS    current
    DESCRIPTION    "This shows the PCI product name of PCI slot of server blade3."
    ::= { blade3InsPCISlotEntry 5 }

blade3InsPCISlotPCISerial    OBJECT-TYPE
    SYNTAX    DisplayString 
    MAX-ACCESS    read-only
    STATUS    current
    DESCRIPTION    "This shows the serial number of PCI slot of server blade3."
    ::= { blade3InsPCISlotEntry 6 }

blade3InsPCISlotPCIManufacturer    OBJECT-TYPE
    SYNTAX    DisplayString 
    MAX-ACCESS    read-only
    STATUS    current
    DESCRIPTION    "This shows the manufacturer of PCI slot of server blade3."
    ::= { blade3InsPCISlotEntry 7 }

blade3InsPCISlotNum    OBJECT-TYPE
    SYNTAX    Integer32
    MAX-ACCESS    read-only
    STATUS    current
    DESCRIPTION    "This shows the number of PCI slots of server blade3."
    ::= { blade3InsPCISlotEntry 8 }

Blade3InsPCISlotEntry ::= SEQUENCE {
    blade3InsPCISlotIndex
        Integer32,
    blade3InsPCISlotType
        DisplayString,
    blade3InsPCISlotExist
        INTEGER,
    blade3InsPCISlotPCIType
        DisplayString,
    blade3InsPCISlotPCIProductName
        DisplayString,
    blade3InsPCISlotPCISerial
        DisplayString,
    blade3InsPCISlotPCIManufacturer
        DisplayString,
    blade3InsPCISlotNum
        Integer32
}

blade3InsLOMTable    OBJECT-TYPE
    SYNTAX SEQUENCE OF blade3InsLOMEntry
    MAX-ACCESS not-accessible
    STATUS     current
    DESCRIPTION "This shows the table of onboard LAN of server blade3."
    ::= { blade3Install 5 }

blade3InsLOMEntry    OBJECT-TYPE
    SYNTAX Blade3InsLOMEntry
    MAX-ACCESS not-accessible
    STATUS    current
    DESCRIPTION "This shows the entry of onboard LAN of server blade3."
    INDEX { blade3InsLOMIndex }
    ::= { blade3InsLOMTable 1 }

blade3InsLOMIndex    OBJECT-TYPE
    SYNTAX    Integer32
    MAX-ACCESS    read-only
    STATUS    current
    DESCRIPTION    "This shows the index of onboard LAN of server blade3."
    ::= { blade3InsLOMEntry 1 }

blade3InsLOMType    OBJECT-TYPE
    SYNTAX    DisplayString 
    MAX-ACCESS    read-only
    STATUS    current
    DESCRIPTION    "This shows the type of onboard LAN of server blade3."
    ::= { blade3InsLOMEntry 2 }

blade3InsLOMLinkSpeed    OBJECT-TYPE
    SYNTAX    Integer32
    UNITS    "bps"
    MAX-ACCESS    read-only
    STATUS    current
    DESCRIPTION    "This shows the link speed of onboard LAN of server blade3."
    ::= { blade3InsLOMEntry 3 }

blade3InsLOMMAC    OBJECT-TYPE
    SYNTAX    DisplayString 
    MAX-ACCESS    read-only
    STATUS    current
    DESCRIPTION    "This shows the MAC address of onboard LAN of server blade3."
    ::= { blade3InsLOMEntry 4 }

blade3InsLOMLinkStatus    OBJECT-TYPE
    SYNTAX    INTEGER {
    up (1),down (2),unknown (3)
    }
    MAX-ACCESS    read-only
    STATUS    current
    DESCRIPTION    "This shows the link state of onboard LAN of server blade3."
    ::= { blade3InsLOMEntry 5 }

blade3InsLOMPortDivide    OBJECT-TYPE
    SYNTAX    INTEGER {
    possible (1),Impossible (2),unknown (3)
    }
    MAX-ACCESS    read-only
    STATUS    current
    DESCRIPTION    "This shows the port divide propriety of onboard LAN of server blade3."
    ::= { blade3InsLOMEntry 6 }

blade3InsLOMPortDivideNum    OBJECT-TYPE
    SYNTAX    Integer32
    MAX-ACCESS    read-only
    STATUS    current
    DESCRIPTION    "This shows the port divide number of onboard LAN of server blade3."
    ::= { blade3InsLOMEntry 7 }

Blade3InsLOMEntry ::= SEQUENCE {
    blade3InsLOMIndex
        Integer32,
    blade3InsLOMType
        DisplayString,
    blade3InsLOMLinkSpeed
        Integer32,
    blade3InsLOMMAC
        DisplayString,
    blade3InsLOMLinkStatus
        INTEGER,
    blade3InsLOMPortDivide
        INTEGER,
    blade3InsLOMPortDivideNum
        Integer32
}

blade3HDDSlotTable    OBJECT-TYPE
    SYNTAX SEQUENCE OF blade3HDDSlotEntry
    MAX-ACCESS not-accessible
    STATUS     current
    DESCRIPTION "This shows the table of HDD slot of server blade3."
    ::= { blade3Install 7 }

blade3HDDSlotEntry    OBJECT-TYPE
    SYNTAX Blade3HDDSlotEntry
    MAX-ACCESS not-accessible
    STATUS    current
    DESCRIPTION "This shows the entry of HDD slot of server blade3."
    INDEX { blade3HDDSlotIndex }
    ::= { blade3HDDSlotTable 1 }

blade3HDDSlotIndex    OBJECT-TYPE
    SYNTAX    Integer32
    MAX-ACCESS    read-only
    STATUS    current
    DESCRIPTION    "This shows the index of HDD slot of server blade3."
    ::= { blade3HDDSlotEntry 1 }

blade3HDDSlotNum    OBJECT-TYPE
    SYNTAX    Integer32
    MAX-ACCESS    read-only
    STATUS    current
    DESCRIPTION    "This shows the number of HDD slots of server blade3."
    ::= { blade3HDDSlotEntry 2 }

blade3HDDSlotExist    OBJECT-TYPE
    SYNTAX    INTEGER {
    non-exist(1), exist(2), unknown(3)
    }
    MAX-ACCESS    read-only
    STATUS    current
    DESCRIPTION    "This shows the registrated state of HDD slot of server blade3."
    ::= { blade3HDDSlotEntry 3 }

blade3HDDSlotHDDType    OBJECT-TYPE
    SYNTAX    DisplayString 
    MAX-ACCESS    read-only
    STATUS    current
    DESCRIPTION    "This shows the HDD type of HDD slot of server blade3."
    ::= { blade3HDDSlotEntry 4 }

blade3HDDSlotHDDProductName    OBJECT-TYPE
    SYNTAX    DisplayString 
    MAX-ACCESS    read-only
    STATUS    current
    DESCRIPTION    "This shows the HDD product name of HDD slot of server blade3."
    ::= { blade3HDDSlotEntry 5 }

blade3HDDSlotHDDModel    OBJECT-TYPE
    SYNTAX    DisplayString 
    MAX-ACCESS    read-only
    STATUS    current
    DESCRIPTION    "This shows the HDD model of HDD slot of server blade3."
    ::= { blade3HDDSlotEntry 6 }

blade3HDDSlotHDDSerialNum    OBJECT-TYPE
    SYNTAX    DisplayString 
    MAX-ACCESS    read-only
    STATUS    current
    DESCRIPTION    "This shows the HDD serial number of HDD slot of server blade3."
    ::= { blade3HDDSlotEntry 7 }

blade3HDDSlotHDDCapacity    OBJECT-TYPE
    SYNTAX    Integer32
    UNITS    "GB"
    MAX-ACCESS    read-only
    STATUS    current
    DESCRIPTION    "This shows the HDD capacity of HDD slots of server blade3."
    ::= { blade3HDDSlotEntry 8 }

blade3HDDSlotHDDRPM    OBJECT-TYPE
    SYNTAX    Integer32
    UNITS    "rpm"
    MAX-ACCESS    read-only
    STATUS    current
    DESCRIPTION    "This shows the HDD drive speed of HDD slot of server blade3."
    ::= { blade3HDDSlotEntry 9 }

blade3HDDSlotHDDStatePower    OBJECT-TYPE
    SYNTAX    INTEGER {
    poweroff (1), poweron (2), unknown (3)
    }
    MAX-ACCESS    read-only
    STATUS    current
    DESCRIPTION    "This shows the HDD power supply state of HDD slot of server blade3."
    ::= { blade3HDDSlotEntry 10 }

blade3HDDSlotHDDStateHealth    OBJECT-TYPE
    SYNTAX    INTEGER {
    normal (1),fail (2),unknown (3),rebuild (4)
    }
    MAX-ACCESS    read-only
    STATUS    current
    DESCRIPTION    "This shows the HDD health state of HDD slot of server blade3."
    ::= { blade3HDDSlotEntry 11 }

blade3HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade3(activity)."
    ::= { blade3HDDSlotEntry 12 }

blade3HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade3(status)."
    ::= { blade3HDDSlotEntry 13 }

blade3HDDSlotHDDFWInfoName    OBJECT-TYPE
    SYNTAX    DisplayString 
    MAX-ACCESS    read-only
    STATUS    current
    DESCRIPTION    "This shows the HDD firmware name of HDD slot of server blade3."
    ::= { blade3HDDSlotEntry 20 }

blade3HDDSlotHDDFWInfoCurrentVer    OBJECT-TYPE
    SYNTAX    DisplayString 
    MAX-ACCESS    read-only
    STATUS    current
    DESCRIPTION    "This shows the HDD firmware current version of HDD slot of server blade3."
    ::= { blade3HDDSlotEntry 21 }

blade3HDDSlotHDDFWInfoNextVer    OBJECT-TYPE
    SYNTAX    DisplayString 
    MAX-ACCESS    read-only
    STATUS    current
    DESCRIPTION    "This shows the HDD firmware next version of HDD slot of server blade3."
    ::= { blade3HDDSlotEntry 22 }

Blade3HDDSlotEntry ::= SEQUENCE {
    blade3HDDSlotIndex
        Integer32,
    blade3HDDSlotNum
        Integer32,
    blade3HDDSlotExist
        INTEGER,
    blade3HDDSlotHDDType
        DisplayString,
    blade3HDDSlotHDDProductName
        DisplayString,
    blade3HDDSlotHDDModel
        DisplayString,
    blade3HDDSlotHDDSerialNum
        DisplayString,
    blade3HDDSlotHDDCapacity
        Integer32,
    blade3HDDSlotHDDRPM
        Integer32,
    blade3HDDSlotHDDStatePower
        INTEGER,
    blade3HDDSlotHDDStateHealth
        INTEGER,
    blade3HDDSlotHDDStateLEDACT
        INTEGER,
    blade3HDDSlotHDDStateLEDSTS
        INTEGER,
    blade3HDDSlotHDDFWInfoName
        DisplayString,
    blade3HDDSlotHDDFWInfoCurrentVer
        DisplayString,
    blade3HDDSlotHDDFWInfoNextVer
        DisplayString
}

blade3ExpansionHDDSlotTable    OBJECT-TYPE
    SYNTAX SEQUENCE OF blade3ExpansionHDDSlotEntry
    MAX-ACCESS not-accessible
    STATUS     current
    DESCRIPTION "This shows the table of expansion HDD slot of server blade3."
    ::= { blade3Install 8 }

blade3ExpansionHDDSlotEntry    OBJECT-TYPE
    SYNTAX Blade3ExpansionHDDSlotEntry
    MAX-ACCESS not-accessible
    STATUS    current
    DESCRIPTION "This shows the entry of expansion HDD slot of server blade3."
    INDEX { blade3ExpansionHDDSlotIndex }
    ::= { blade3ExpansionHDDSlotTable 1 }

blade3ExpansionHDDSlotIndex    OBJECT-TYPE
    SYNTAX    Integer32
    MAX-ACCESS    read-only
    STATUS    current
    DESCRIPTION    "This shows the index of expansion HDD slot of server blade3."
    ::= { blade3ExpansionHDDSlotEntry 1 }

blade3ExpansionHDDSlotNum    OBJECT-TYPE
    SYNTAX    Integer32
    MAX-ACCESS    read-only
    STATUS    current
    DESCRIPTION    "This shows the number of expansion HDD slots of server blade3."
    ::= { blade3ExpansionHDDSlotEntry 2 }

blade3ExpansionHDDSlotExist    OBJECT-TYPE
    SYNTAX    INTEGER {
    non-exist(1), exist(2), unknown(3)
    }
    MAX-ACCESS    read-only
    STATUS    current
    DESCRIPTION    "This shows the registrated state of expansion HDD slot of server blade3."
    ::= { blade3ExpansionHDDSlotEntry 3 }

blade3ExpansionHDDSlotHDDType    OBJECT-TYPE
    SYNTAX    DisplayString 
    MAX-ACCESS    read-only
    STATUS    current
    DESCRIPTION    "This shows the HDD type of expansion HDD slot of server blade3."
    ::= { blade3ExpansionHDDSlotEntry 4 }

blade3ExpansionHDDSlotHDDProductName    OBJECT-TYPE
    SYNTAX    DisplayString 
    MAX-ACCESS    read-only
    STATUS    current
    DESCRIPTION    "This shows the HDD product name of expansion HDD slot of server blade3."
    ::= { blade3ExpansionHDDSlotEntry 5 }

blade3ExpansionHDDSlotHDDModel    OBJECT-TYPE
    SYNTAX    DisplayString 
    MAX-ACCESS    read-only
    STATUS    current
    DESCRIPTION    "This shows the HDD model of expansion HDD slot of server blade3."
    ::= { blade3ExpansionHDDSlotEntry 6 }

blade3ExpansionHDDSlotHDDSerialNum    OBJECT-TYPE
    SYNTAX    DisplayString 
    MAX-ACCESS    read-only
    STATUS    current
    DESCRIPTION    "This shows the HDD serial number of expansion HDD slot of server blade3."
    ::= { blade3ExpansionHDDSlotEntry 7 }

blade3ExpansionHDDSlotHDDCapacity    OBJECT-TYPE
    SYNTAX    Integer32
    UNITS    "GB"
    MAX-ACCESS    read-only
    STATUS    current
    DESCRIPTION    "This shows the HDD capacity of expansion HDD slots of server blade3."
    ::= { blade3ExpansionHDDSlotEntry 8 }

blade3ExpansionHDDSlotHDDRPM    OBJECT-TYPE
    SYNTAX    Integer32
    UNITS    "rpm"
    MAX-ACCESS    read-only
    STATUS    current
    DESCRIPTION    "This shows the HDD drive speed of expansion HDD slot of server blade3."
    ::= { blade3ExpansionHDDSlotEntry 9 }

blade3ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade3."
    ::= { blade3ExpansionHDDSlotEntry 10 }

blade3ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade3."
    ::= { blade3ExpansionHDDSlotEntry 11 }

blade3ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade3(activity)."
    ::= { blade3ExpansionHDDSlotEntry 12 }

blade3ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade3(status)."
    ::= { blade3ExpansionHDDSlotEntry 13 }

blade3ExpansionHDDSlotHDDFWInfoName    OBJECT-TYPE
    SYNTAX    DisplayString 
    MAX-ACCESS    read-only
    STATUS    current
    DESCRIPTION    "This shows the HDD firmware name of expansion HDD slot of server blade3."
    ::= { blade3ExpansionHDDSlotEntry 20 }

blade3ExpansionHDDSlotHDDFWInfoCurrentVer    OBJECT-TYPE
    SYNTAX    DisplayString 
    MAX-ACCESS    read-only
    STATUS    current
    DESCRIPTION    "This shows the HDD firmware current version of expansion HDD slot of server blade3."
    ::= { blade3ExpansionHDDSlotEntry 21 }

blade3ExpansionHDDSlotHDDFWInfoNextVer    OBJECT-TYPE
    SYNTAX    DisplayString 
    MAX-ACCESS    read-only
    STATUS    current
    DESCRIPTION    "This shows the HDD firmware next version of expansion HDD slot of server blade3."
    ::= { blade3ExpansionHDDSlotEntry 22 }

Blade3ExpansionHDDSlotEntry ::= SEQUENCE {
    blade3ExpansionHDDSlotIndex
        Integer32,
    blade3ExpansionHDDSlotNum
        Integer32,
    blade3ExpansionHDDSlotExist
        INTEGER,
    blade3ExpansionHDDSlotHDDType
        DisplayString,
    blade3ExpansionHDDSlotHDDProductName
        DisplayString,
    blade3ExpansionHDDSlotHDDModel
        DisplayString,
    blade3ExpansionHDDSlotHDDSerialNum
        DisplayString,
    blade3ExpansionHDDSlotHDDCapacity
        Integer32,
    blade3ExpansionHDDSlotHDDRPM
        Integer32,
    blade3ExpansionHDDSlotHDDStatePower
        INTEGER,
    blade3ExpansionHDDSlotHDDStateHealth
        INTEGER,
    blade3ExpansionHDDSlotHDDStateLEDACT
        INTEGER,
    blade3ExpansionHDDSlotHDDStateLEDSTS
        INTEGER,
    blade3ExpansionHDDSlotHDDFWInfoName
        DisplayString,
    blade3ExpansionHDDSlotHDDFWInfoCurrentVer
        DisplayString,
    blade3ExpansionHDDSlotHDDFWInfoNextVer
        DisplayString
}

blade3VoltageSensorTable    OBJECT-TYPE
    SYNTAX SEQUENCE OF blade3VoltageSensorEntry
    MAX-ACCESS not-accessible
    STATUS     current
    DESCRIPTION "This shows the table of voltage sensor of server blade3."
    ::= { blade3State 40 }

blade3VoltageSensorEntry    OBJECT-TYPE
    SYNTAX Blade3VoltageSensorEntry
    MAX-ACCESS not-accessible
    STATUS    current
    DESCRIPTION "This shows the entry of voltage sensor of server blade3."
    INDEX { blade3VoltageSensorIndex }
    ::= { blade3VoltageSensorTable 1 }

blade3VoltageSensorIndex    OBJECT-TYPE
    SYNTAX    Integer32
    MAX-ACCESS    read-only
    STATUS    current
    DESCRIPTION    "This shows the index of voltage sensor of server blade3."
    ::= { blade3VoltageSensorEntry 1 }

blade3VoltageSensorName    OBJECT-TYPE
    SYNTAX    DisplayString 
    MAX-ACCESS    read-only
    STATUS    current
    DESCRIPTION    "This shows the voltage sensor name of server blade3."
    ::= { blade3VoltageSensorEntry 2 }

blade3VoltageSensorValue    OBJECT-TYPE
    SYNTAX    Integer32
    UNITS    "0.1 V"
    MAX-ACCESS    read-only
    STATUS    current
    DESCRIPTION    "This shows the voltage sensor value of server blade3."
    ::= { blade3VoltageSensorEntry 3 }

blade3VoltageSensorValid    OBJECT-TYPE
    SYNTAX    INTEGER {
    invalid (1),valid (2),unknown (3)
    }
    MAX-ACCESS    read-only
    STATUS    current
    DESCRIPTION    "This shows the validity of voltage sensor value of server blade3."
    ::= { blade3VoltageSensorEntry 4 }

Blade3VoltageSensorEntry ::= SEQUENCE {
    blade3VoltageSensorIndex
        Integer32,
    blade3VoltageSensorName
        DisplayString,
    blade3VoltageSensorValue
        Integer32,
    blade3VoltageSensorValid
        INTEGER
}

blade3TempSensorTable    OBJECT-TYPE
    SYNTAX SEQUENCE OF blade3TempSensorEntry
    MAX-ACCESS not-accessible
    STATUS     current
    DESCRIPTION "This shows the table of temperature sensor of server blade3."
    ::= { blade3State 41 }

blade3TempSensorEntry    OBJECT-TYPE
    SYNTAX Blade3TempSensorEntry
    MAX-ACCESS not-accessible
    STATUS    current
    DESCRIPTION "This shows the entry of temperature sensor of server blade3."
    INDEX { blade3TempSensorIndex }
    ::= { blade3TempSensorTable 1 }

blade3TempSensorIndex    OBJECT-TYPE
    SYNTAX    Integer32
    MAX-ACCESS    read-only
    STATUS    current
    DESCRIPTION    "This shows the index of temperature sensor of server blade3."
    ::= { blade3TempSensorEntry 1 }

blade3TempSensorName    OBJECT-TYPE
    SYNTAX    DisplayString 
    MAX-ACCESS    read-only
    STATUS    current
    DESCRIPTION    "This shows the temperature sensor name of server blade3."
    ::= { blade3TempSensorEntry 2 }

blade3TempSensorValue    OBJECT-TYPE
    SYNTAX    Integer32
    UNITS    "0.1 degrees C"
    MAX-ACCESS    read-only
    STATUS    current
    DESCRIPTION    "This shows the temperature sensor value of server blade3."
    ::= { blade3TempSensorEntry 3 }

blade3TempSensorValid    OBJECT-TYPE
    SYNTAX    INTEGER {
    invalid (1),valid (2),unknown (3)
    }
    MAX-ACCESS    read-only
    STATUS    current
    DESCRIPTION    "This shows the validity of temperature sensor value of server blade3."
    ::= { blade3TempSensorEntry 4 }

Blade3TempSensorEntry ::= SEQUENCE {
    blade3TempSensorIndex
        Integer32,
    blade3TempSensorName
        DisplayString,
    blade3TempSensorValue
        Integer32,
    blade3TempSensorValid
        INTEGER
}

blade3FWInfo    OBJECT IDENTIFIER ::= { blade3 5 } 

blade3FWInfoTotalCurrentVer    OBJECT-TYPE
    SYNTAX    DisplayString (SIZE(0..40))
    MAX-ACCESS    read-only
    STATUS    current
    DESCRIPTION    "This shows the total current version of firmware of server blade3."
    ::= { blade3FWInfo 1 }

blade3FWInfoTotalNextVer    OBJECT-TYPE
    SYNTAX    DisplayString (SIZE(0..40))
    MAX-ACCESS    read-only
    STATUS    current
    DESCRIPTION    "This shows the total next version of firmware of server blade3."
    ::= { blade3FWInfo 2 }

blade3FWInfoTable    OBJECT-TYPE
    SYNTAX SEQUENCE OF blade3FWInfoEntry
    MAX-ACCESS not-accessible
    STATUS     current
    DESCRIPTION "This shows the table of firmware information of server blade3."
    ::= { blade3FWInfo 3 }

blade3FWInfoEntry    OBJECT-TYPE
    SYNTAX Blade3FWInfoEntry
    MAX-ACCESS not-accessible
    STATUS    current
    DESCRIPTION "This shows the entry of firmware information of server blade3."
    INDEX { blade3FWInfoIndex }
    ::= { blade3FWInfoTable 1 }

blade3FWInfoIndex    OBJECT-TYPE
    SYNTAX    Integer32
    MAX-ACCESS    read-only
    STATUS    current
    DESCRIPTION    "This shows the index of firmware information of server blade3."
    ::= { blade3FWInfoEntry 1 }

blade3FWInfoName    OBJECT-TYPE
    SYNTAX    DisplayString (SIZE(0..40))
    MAX-ACCESS    read-only
    STATUS    current
    DESCRIPTION    "This shows the firmware name of server blade3."
    ::= { blade3FWInfoEntry 2 }

blade3FWCurrentVer    OBJECT-TYPE
    SYNTAX    DisplayString (SIZE(0..40))
    MAX-ACCESS    read-only
    STATUS    current
    DESCRIPTION    "This shows the firmware current version of server blade3."
    ::= { blade3FWInfoEntry 3 }

blade3FWInfoNextVer    OBJECT-TYPE
    SYNTAX    DisplayString (SIZE(0..40))
    MAX-ACCESS    read-only
    STATUS    current
    DESCRIPTION    "This shows the firmware next version of server blade3."
    ::= { blade3FWInfoEntry 4 }

blade3FWInfoHVMCurrentVer    OBJECT-TYPE
    SYNTAX    DisplayString (SIZE(0..40))
    MAX-ACCESS    read-only
    STATUS    current
    DESCRIPTION    "This shows the HVM current version of server blade3."
    ::= { blade3FWInfo 4 }

blade3FWInfoHVMNextVer    OBJECT-TYPE
    SYNTAX    DisplayString (SIZE(0..40))
    MAX-ACCESS    read-only
    STATUS    current
    DESCRIPTION    "This shows the HVM next version of server blade3."
    ::= { blade3FWInfo 5 }

Blade3FWInfoEntry ::= SEQUENCE {
    blade3FWInfoIndex
        Integer32,
    blade3FWInfoName
        DisplayString,
    blade3FWCurrentVer
        DisplayString,
    blade3FWInfoNextVer
        DisplayString,
    blade3FWInfoHVMCurrentVer
        DisplayString,
    blade3FWInfoHVMNextVer
        DisplayString
}

blade4    OBJECT IDENTIFIER ::= { blade 4 } 

blade4BasicInfo    OBJECT IDENTIFIER ::= { blade4 1 } 

blade4InfoProductName    OBJECT-TYPE
    SYNTAX    DisplayString (SIZE(0..40))
    MAX-ACCESS    read-only
    STATUS    current
    DESCRIPTION    "This shows the product name of server blade4."
    ::= { blade4BasicInfo 1 }

blade4InfoModel    OBJECT-TYPE
    SYNTAX    DisplayString (SIZE(0..40))
    MAX-ACCESS    read-only
    STATUS    current
    DESCRIPTION    "This shows the model name of server blade4."
    ::= { blade4BasicInfo 2 }

blade4InfoSerialNum    OBJECT-TYPE
    SYNTAX    DisplayString (SIZE(0..40))
    MAX-ACCESS    read-only
    STATUS    current
    DESCRIPTION    "This shows the serial number of server blade4."
    ::= { blade4BasicInfo 3 }

blade4InfoProductVersion    OBJECT-TYPE
    SYNTAX    DisplayString (SIZE(0..40))
    MAX-ACCESS    read-only
    STATUS    current
    DESCRIPTION    "This shows the product version of server blade4."
    ::= { blade4BasicInfo 4 }

blade4InfoProductManufacturer    OBJECT-TYPE
    SYNTAX    DisplayString (SIZE(0..40))
    MAX-ACCESS    read-only
    STATUS    current
    DESCRIPTION    "This shows the product manufacturer of server blade4."
    ::= { blade4BasicInfo 5 }

blade4InfoBoardProductName    OBJECT-TYPE
    SYNTAX    DisplayString (SIZE(0..40))
    MAX-ACCESS    read-only
    STATUS    current
    DESCRIPTION    "This shows the board product name of server blade4."
    ::= { blade4BasicInfo 7 }

blade4InfoBoardSerialNum    OBJECT-TYPE
    SYNTAX    DisplayString (SIZE(0..40))
    MAX-ACCESS    read-only
    STATUS    current
    DESCRIPTION    "This shows the board serial number of server blade4."
    ::= { blade4BasicInfo 8 }

blade4InfoBoardManufacturer    OBJECT-TYPE
    SYNTAX    DisplayString (SIZE(0..40))
    MAX-ACCESS    read-only
    STATUS    current
    DESCRIPTION    "This shows the board manufacturer of server blade4."
    ::= { blade4BasicInfo 9 }

blade4InfoUUID    OBJECT-TYPE
    SYNTAX    DisplayString (SIZE(0..40))
    MAX-ACCESS    read-only
    STATUS    current
    DESCRIPTION    "This shows UUID(universal Unique ID) of server blade4."
    ::= { blade4BasicInfo 10 }

blade4InfoLogicalPartitionSupport    OBJECT-TYPE
    SYNTAX    INTEGER {
    not-support(1), support(2),unknown(3)
    }
    MAX-ACCESS    read-only
    STATUS    current
    DESCRIPTION    "This shows whether the server blade4 supports HVM or not of server blade1."
    ::= { blade4BasicInfo 11 }

blade4InfoRemoteKVMSupport    OBJECT-TYPE
    SYNTAX    INTEGER {
    not-support(1), support(2),unknown(3)
    }
    MAX-ACCESS    read-only
    STATUS    current
    DESCRIPTION    "This shows whether the server blade4 supports remote KVM or not of server blade1."
    ::= { blade4BasicInfo 12 }

blade4InfoSpec    OBJECT IDENTIFIER ::= { blade4BasicInfo 20 } 

blade4SpecInputCurrentType    OBJECT-TYPE
    SYNTAX    INTEGER {
    ac(1),dc(2),unknown(3)
    }
    MAX-ACCESS    read-only
    STATUS    current
    DESCRIPTION    "This shows the currency type of server blade4."
    ::= { blade4InfoSpec 1 }

blade4SpecRateVoltage    OBJECT-TYPE
    SYNTAX    Integer32
    UNITS    "0.1 V"
    MAX-ACCESS    read-only
    STATUS    current
    DESCRIPTION    "This shows the rated voltage of server blade4."
    ::= { blade4InfoSpec 2 }

blade4SpecConsumptionCurrent    OBJECT-TYPE
    SYNTAX    Integer32
    UNITS    "0.1 A"
    MAX-ACCESS    read-only
    STATUS    current
    DESCRIPTION    "This shows the consumption current of server blade4."
    ::= { blade4InfoSpec 3 }

blade4SpecPowerConsumption    OBJECT-TYPE
    SYNTAX    Integer32
    UNITS    "W"
    MAX-ACCESS    read-only
    STATUS    current
    DESCRIPTION    "This shows the power consumption of server blade4."
    ::= { blade4InfoSpec 4 }

blade4SpecMass    OBJECT-TYPE
    SYNTAX    Integer32
    UNITS    "0.1 kg"
    MAX-ACCESS    read-only
    STATUS    current
    DESCRIPTION    "This shows the weight of server blade4."
    ::= { blade4InfoSpec 5 }

blade4InfoUpperLimitIntakeTemp    OBJECT-TYPE
    SYNTAX    Integer32
    UNITS    "0.1 degrees C"
    MAX-ACCESS    read-only
    STATUS    current
    DESCRIPTION    "This shows the maximum limited intake temperature of server blade4."
    ::= { blade4InfoSpec 6 }

blade4InfoLowerLimitIntakeTemp    OBJECT-TYPE
    SYNTAX    Integer32
    UNITS    "0.1 degrees C"
    MAX-ACCESS    read-only
    STATUS    current
    DESCRIPTION    "This shows the minimum limited intake temperature of server blade4."
    ::= { blade4InfoSpec 7 }

blade4SpecSize    OBJECT-TYPE
    SYNTAX    DisplayString (SIZE(0..40))
    MAX-ACCESS    read-only
    STATUS    current
    DESCRIPTION    "This shows the size of server blade4."
    ::= { blade4InfoSpec 8 }

blade4SpecOccupySlots    OBJECT-TYPE
    SYNTAX    Integer32
    MAX-ACCESS    read-only
    STATUS    current
    DESCRIPTION    "This shows the dedicated number of slots of server blade4."
    ::= { blade4InfoSpec 9 }

blade4SpecExpansionBladeSlot    OBJECT-TYPE
    SYNTAX    Integer32
    MAX-ACCESS    read-only
    STATUS    current
    DESCRIPTION    "This shows the number of slots of expansion blade of server blade4."
    ::= { blade4InfoSpec 10 }

blade4InfoExpansionBladeTable    OBJECT-TYPE
    SYNTAX SEQUENCE OF blade4InfoExpansionBladeEntry
    MAX-ACCESS not-accessible
    STATUS     current
    DESCRIPTION "This shows the table of expansion blade slot of server blade4."
    ::= { blade4BasicInfo 30 }

blade4InfoExpansionBladeEntry    OBJECT-TYPE
    SYNTAX Blade4InfoExpansionBladeEntry
    MAX-ACCESS not-accessible
    STATUS    current
    DESCRIPTION "This shows the entry of expansion blade slot of server blade4."
    INDEX { blade4InfoExpansionBladeIndex }
    ::= { blade4InfoExpansionBladeTable 1 }

blade4InfoExpansionBladeIndex    OBJECT-TYPE
    SYNTAX    Integer32
    MAX-ACCESS    read-only
    STATUS    current
    DESCRIPTION    "This shows the index of expansion blade slot of server blade4."
    ::= { blade4InfoExpansionBladeEntry 1 }

blade4InfoExpansionBladeExist    OBJECT-TYPE
    SYNTAX    INTEGER {
    non-exist(1), exist(2), unknown(3)
    }
    MAX-ACCESS    read-only
    STATUS    current
    DESCRIPTION    "This shows the registrated state of expansion blade of server blade4."
    ::= { blade4InfoExpansionBladeEntry 2 }

blade4InfoExpansionBladeProductName    OBJECT-TYPE
    SYNTAX    DisplayString (SIZE(0..40))
    MAX-ACCESS    read-only
    STATUS    current
    DESCRIPTION    "This shows the product name of expansion blade of server blade4."
    ::= { blade4InfoExpansionBladeEntry 3 }

blade4InfoExpansionBladeModel    OBJECT-TYPE
    SYNTAX    DisplayString (SIZE(0..40))
    MAX-ACCESS    read-only
    STATUS    current
    DESCRIPTION    "This shows the model name of expansion blade of server blade4."
    ::= { blade4InfoExpansionBladeEntry 4 }

blade4InfoExpansionBladeSerialNum    OBJECT-TYPE
    SYNTAX    DisplayString (SIZE(0..40))
    MAX-ACCESS    read-only
    STATUS    current
    DESCRIPTION    "This shows the serial number of expansion blade of server blade4."
    ::= { blade4InfoExpansionBladeEntry 5 }

blade4InfoExpansionBladeProductVersion    OBJECT-TYPE
    SYNTAX    DisplayString (SIZE(0..40))
    MAX-ACCESS    read-only
    STATUS    current
    DESCRIPTION    "This shows the product version of expansion blade of server blade4."
    ::= { blade4InfoExpansionBladeEntry 6 }

blade4InfoExpansionBladeProductManufacturer    OBJECT-TYPE
    SYNTAX    DisplayString (SIZE(0..40))
    MAX-ACCESS    read-only
    STATUS    current
    DESCRIPTION    "This shows the product manufacturer of expansion blade of server blade4."
    ::= { blade4InfoExpansionBladeEntry 7 }

blade4InfoExpansionBladeBoardProductName    OBJECT-TYPE
    SYNTAX    DisplayString (SIZE(0..40))
    MAX-ACCESS    read-only
    STATUS    current
    DESCRIPTION    "This shows the board product name of expansion blade of server blade4."
    ::= { blade4InfoExpansionBladeEntry 9 }

blade4InfoExpansionBladeBoardSerialNum    OBJECT-TYPE
    SYNTAX    DisplayString (SIZE(0..40))
    MAX-ACCESS    read-only
    STATUS    current
    DESCRIPTION    "This shows the board serial number of expansion blade of server blade4."
    ::= { blade4InfoExpansionBladeEntry 10 }

blade4InfoExpansionBladeBoardManufacturer    OBJECT-TYPE
    SYNTAX    DisplayString (SIZE(0..40))
    MAX-ACCESS    read-only
    STATUS    current
    DESCRIPTION    "This shows the board manufacturer of expansion blade of server blade4."
    ::= { blade4InfoExpansionBladeEntry 11 }

Blade4InfoExpansionBladeEntry ::= SEQUENCE {
    blade4InfoExpansionBladeIndex
        Integer32,
    blade4InfoExpansionBladeExist
        INTEGER,
    blade4InfoExpansionBladeProductName
        DisplayString,
    blade4InfoExpansionBladeModel
        DisplayString,
    blade4InfoExpansionBladeSerialNum
        DisplayString,
    blade4InfoExpansionBladeProductVersion
        DisplayString,
    blade4InfoExpansionBladeProductManufacturer
        DisplayString,
    blade4InfoExpansionBladeBoardProductName
        DisplayString,
    blade4InfoExpansionBladeBoardSerialNum
        DisplayString,
    blade4InfoExpansionBladeBoardManufacturer
        DisplayString
}

blade4Capacity    OBJECT IDENTIFIER ::= { blade4 2 } 

blade4CapacityCPUSocket    OBJECT-TYPE
    SYNTAX    Integer32
    MAX-ACCESS    read-only
    STATUS    current
    DESCRIPTION    "This shows the capacity of CPU sockets of server blade4."
    ::= { blade4Capacity 1 }

blade4CapacityDIMMSlot    OBJECT-TYPE
    SYNTAX    Integer32
    MAX-ACCESS    read-only
    STATUS    current
    DESCRIPTION    "This shows the capacity of DIMM slots of server blade4."
    ::= { blade4Capacity 2 }

blade4CapacityPCISlot    OBJECT-TYPE
    SYNTAX    Integer32
    MAX-ACCESS    read-only
    STATUS    current
    DESCRIPTION    "This shows the capacity of PCI slots of server blade4."
    ::= { blade4Capacity 3 }

blade4CapacityLOM    OBJECT-TYPE
    SYNTAX    Integer32
    MAX-ACCESS    read-only
    STATUS    current
    DESCRIPTION    "This shows the capacity of onboard LAN ports of server blade4."
    ::= { blade4Capacity 4 }

blade4CapacityFan    OBJECT-TYPE
    SYNTAX    Integer32
    MAX-ACCESS    read-only
    STATUS    current
    DESCRIPTION    "This shows the capacity of onboard fans of server blade4."
    ::= { blade4Capacity 5 }

blade4CapacityHDDSlot    OBJECT-TYPE
    SYNTAX    Integer32
    MAX-ACCESS    read-only
    STATUS    current
    DESCRIPTION    "This shows the capacity of HDD slots of server blade4."
    ::= { blade4Capacity 6 }

blade4CapacityVoltageSensor    OBJECT-TYPE
    SYNTAX    Integer32
    MAX-ACCESS    read-only
    STATUS    current
    DESCRIPTION    "This shows the capacity of voltage sensors of blade4."
    ::= { blade4Capacity 7 }

blade4CapacityTempSensor    OBJECT-TYPE
    SYNTAX    Integer32
    MAX-ACCESS    read-only
    STATUS    current
    DESCRIPTION    "This shows the capacity of temperature sensors of blade4."
    ::= { blade4Capacity 8 }

blade4CapacityExpansionHDDSlot    OBJECT-TYPE
    SYNTAX    Integer32
    MAX-ACCESS    read-only
    STATUS    current
    DESCRIPTION    "This shows the capacity of expansion HDD slots of server blade4."
    ::= { blade4Capacity 9 }

blade4CapacityLED    OBJECT-TYPE
    SYNTAX    Integer32
    MAX-ACCESS    read-only
    STATUS    current
    DESCRIPTION    "This shows the capacity of count of LEDs of server blade4."
    ::= { blade4Capacity 10 }

blade4Settings    OBJECT IDENTIFIER ::= { blade4 3 } 

blade4SettingsBelongPartitionNum    OBJECT-TYPE
    SYNTAX    Integer32
    MAX-ACCESS    read-only
    STATUS    current
    DESCRIPTION    "This shows the partition number of server blade4."
    ::= { blade4Settings 1 }

blade4SettingsDetailHVMLicenceModel    OBJECT-TYPE
    SYNTAX    DisplayString (SIZE(0..40))
    MAX-ACCESS    read-only
    STATUS    current
    DESCRIPTION    "This shows the HVM licence of detailed server blade4 (model). "
    ::= { blade4Settings 2 }

blade4SettingsDetailHVMLicenceAvailableVersion    OBJECT-TYPE
    SYNTAX    DisplayString (SIZE(0..40))
    MAX-ACCESS    read-only
    STATUS    current
    DESCRIPTION    "This shows the HVM licence of detailed server blade4 (available version). "
    ::= { blade4Settings 3 }

blade4SettingsManagementPortIPAddress    OBJECT-TYPE
    SYNTAX    DisplayString (SIZE(0..40))
    MAX-ACCESS    read-only
    STATUS    current
    DESCRIPTION    "This shows the IP address of management port of server blade4."
    ::= { blade4Settings 4 }

blade4State    OBJECT IDENTIFIER ::= { blade4 4 } 

blade4StateSlotNum    OBJECT-TYPE
    SYNTAX    Integer32
    MAX-ACCESS    read-only
    STATUS    current
    DESCRIPTION    "This shows the number of installed slots of server blade4."
    ::= { blade4State 1 }

blade4StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade4."
    ::= { blade4State 2 }

blade4StateHealth    OBJECT-TYPE
    SYNTAX    INTEGER {
    normal (1),fail (2),unknown (3)
    }
    MAX-ACCESS    read-only
    STATUS    current
    DESCRIPTION    "This shows the health state of server blade4."
    ::= { blade4State 3 }

blade4StatePrimaly    OBJECT-TYPE
    SYNTAX    INTEGER {
    primary(1), non-primary(2),unknown(3)
    }
    MAX-ACCESS    read-only
    STATUS    current
    DESCRIPTION    "This shows the primary state of server blade4."
    ::= { blade4State 4 }

blade4StateCurrentVoltage    OBJECT-TYPE
    SYNTAX    Integer32
    UNITS    "0.1 V"
    MAX-ACCESS    read-only
    STATUS    current
    DESCRIPTION    "This shows the current voltage of server blade4."
    ::= { blade4State 5 }

blade4StateConsumptionCurrent    OBJECT-TYPE
    SYNTAX    Integer32
    UNITS    "0.1 A"
    MAX-ACCESS    read-only
    STATUS    current
    DESCRIPTION    "This shows the consumption current of server blade4."
    ::= { blade4State 6 }

blade4StatePowerConsumption    OBJECT-TYPE
    SYNTAX    Integer32
    UNITS    "W"
    MAX-ACCESS    read-only
    STATUS    current
    DESCRIPTION    "This shows the power consumption of server blade4."
    ::= { blade4State 7 }

blade4StateIntakeTemp    OBJECT-TYPE
    SYNTAX    INTEGER {
    normal (1), higher-warning (2), higher-error (3), lower-warning (4), unknown(5)
    }
    MAX-ACCESS    read-only
    STATUS    current
    DESCRIPTION    "This shows the state of intake temperature of server blade4."
    ::= { blade4State 8 }

blade4StateLEDTable    OBJECT-TYPE
    SYNTAX SEQUENCE OF blade4StateLEDEntry
    MAX-ACCESS not-accessible
    STATUS     current
    DESCRIPTION "This shows the table of LED of server blade4."
    ::= { blade4State 9 }

blade4StateLEDEntry    OBJECT-TYPE
    SYNTAX Blade4StateLEDEntry
    MAX-ACCESS not-accessible
    STATUS    current
    DESCRIPTION "This shows the entry of LED of server blade4."
    INDEX { blade4StateLEDIndex }
    ::= { blade4StateLEDTable 1 }

blade4StateLEDIndex    OBJECT-TYPE
    SYNTAX    Integer32
    MAX-ACCESS    read-only
    STATUS    current
    DESCRIPTION    "This shows the index of LED of server blade4."
    ::= { blade4StateLEDEntry 1 }

blade4StateLEDName    OBJECT-TYPE
    SYNTAX    DisplayString (SIZE(0..40))
    MAX-ACCESS    read-only
    STATUS    current
    DESCRIPTION    "This shows the name of LED of server blade4."
    ::= { blade4StateLEDEntry 2 }

blade4StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade4."
    ::= { blade4StateLEDEntry 3 }

blade4StateLEDColor    OBJECT-TYPE
    SYNTAX    INTEGER {
    blue (1),green (2),red (3),amber (4),unknown (5)
    }
    MAX-ACCESS    read-only
    STATUS    current
    DESCRIPTION    "This shows the color of LED of server blade4."
    ::= { blade4StateLEDEntry 4 }

Blade4StateLEDEntry ::= SEQUENCE {
    blade4StateLEDIndex
        Integer32,
    blade4StateLEDName
        DisplayString,
    blade4StateLEDState
        INTEGER,
    blade4StateLEDColor
        INTEGER
}

blade4StateOther    OBJECT IDENTIFIER ::= { blade4State 20 } 

blade4MaintMode    OBJECT-TYPE
    SYNTAX    INTEGER {
    Normal(1), CE-Maint-mode(2), User-Maint-mode(3), unknown(4)
    }
    MAX-ACCESS    read-only
    STATUS    current
    DESCRIPTION    "This shows the maintenance mode of server blade4."
    ::= { blade4StateOther 1 }

blade4Install    OBJECT IDENTIFIER ::= { blade4State 30 } 

blade4InsCPUSocketTable    OBJECT-TYPE
    SYNTAX SEQUENCE OF blade4InsCPUSocketEntry
    MAX-ACCESS not-accessible
    STATUS     current
    DESCRIPTION "This shows the table of CPU socket of server blade4."
    ::= { blade4Install 1 }

blade4InsCPUSocketEntry    OBJECT-TYPE
    SYNTAX Blade4InsCPUSocketEntry
    MAX-ACCESS not-accessible
    STATUS    current
    DESCRIPTION "This shows the entry of CPU socket of server blade4."
    INDEX { blade4InsCPUSocketIndex }
    ::= { blade4InsCPUSocketTable 1 }

blade4InsCPUSocketIndex    OBJECT-TYPE
    SYNTAX    Integer32
    MAX-ACCESS    read-only
    STATUS    current
    DESCRIPTION    "This shows the index of CPU socket of server blade4."
    ::= { blade4InsCPUSocketEntry 1 }

blade4InsCPUSocketNum    OBJECT-TYPE
    SYNTAX    Integer32
    MAX-ACCESS    read-only
    STATUS    current
    DESCRIPTION    "This shows the number of CPU sockets of server blade4."
    ::= { blade4InsCPUSocketEntry 2 }

blade4InsCPUSocketExist    OBJECT-TYPE
    SYNTAX    INTEGER {
    non-exist(1), exist(2), unknown(3)
    }
    MAX-ACCESS    read-only
    STATUS    current
    DESCRIPTION    "This shows the registrated state of CPU socket of server blade4."
    ::= { blade4InsCPUSocketEntry 3 }

blade4InsCPUSocketCPUName    OBJECT-TYPE
    SYNTAX    DisplayString (SIZE(0..40))
    MAX-ACCESS    read-only
    STATUS    current
    DESCRIPTION    "This shows the CPU name of CPU socket of server blade4."
    ::= { blade4InsCPUSocketEntry 4 }

blade4InsCPUSocketCPUFrequency    OBJECT-TYPE
    SYNTAX    Integer32
    UNITS    "MHz"
    MAX-ACCESS    read-only
    STATUS    current
    DESCRIPTION    "This shows the CPU frequency of CPU socket of server blade4."
    ::= { blade4InsCPUSocketEntry 5 }

blade4InsCPUSocketCPUStepping    OBJECT-TYPE
    SYNTAX    DisplayString 
    MAX-ACCESS    read-only
    STATUS    current
    DESCRIPTION    "This shows the CPU stepping of CPU socket of server blade4."
    ::= { blade4InsCPUSocketEntry 6 }

blade4InsCPUSocketCPUCoreNum    OBJECT-TYPE
    SYNTAX    Integer32
    MAX-ACCESS    read-only
    STATUS    current
    DESCRIPTION    "This shows the CPU core number of CPU socket of server blade4."
    ::= { blade4InsCPUSocketEntry 7 }

blade4InsCPUSocketCPUUpperLimitTemp    OBJECT-TYPE
    SYNTAX    Integer32
    UNITS    "0.1 degrees C"
    MAX-ACCESS    read-only
    STATUS    current
    DESCRIPTION    "This shows the maximum limited CPU temperature of server blade4."
    ::= { blade4InsCPUSocketEntry 8 }

blade4InsCPUSocketCPULowerLimitTemp    OBJECT-TYPE
    SYNTAX    Integer32
    UNITS    "0.1 degrees C"
    MAX-ACCESS    read-only
    STATUS    current
    DESCRIPTION    "This shows the minimum limited CPU temperature of server blade4."
    ::= { blade4InsCPUSocketEntry 9 }

blade4InsDIMMCapacity    OBJECT-TYPE
    SYNTAX    Integer32
    UNITS    "GB"
    MAX-ACCESS    read-only
    STATUS    current
    DESCRIPTION    "This shows the total amount of DIMM capacity of server blade4."
    ::= { blade4Install 2 }

Blade4InsCPUSocketEntry ::= SEQUENCE {
    blade4InsCPUSocketIndex
        Integer32,
    blade4InsCPUSocketNum
        Integer32,
    blade4InsCPUSocketExist
        INTEGER,
    blade4InsCPUSocketCPUName
        DisplayString,
    blade4InsCPUSocketCPUFrequency
        Integer32,
    blade4InsCPUSocketCPUStepping
        DisplayString,
    blade4InsCPUSocketCPUCoreNum
        Integer32,
    blade4InsCPUSocketCPUUpperLimitTemp
        Integer32,
    blade4InsCPUSocketCPULowerLimitTemp
        Integer32,
    blade4InsDIMMCapacity
        Integer32
}

blade4InsDIMMSlotTable    OBJECT-TYPE
    SYNTAX SEQUENCE OF blade4InsDIMMSlotEntry
    MAX-ACCESS not-accessible
    STATUS     current
    DESCRIPTION "This shows the table of DIMM slot of server blade4."
    ::= { blade4Install 3 }

blade4InsDIMMSlotEntry    OBJECT-TYPE
    SYNTAX Blade4InsDIMMSlotEntry
    MAX-ACCESS not-accessible
    STATUS    current
    DESCRIPTION "This shows the entry of DIMM slot of server blade4."
    INDEX { blade4InsDIMMSlotIndex }
    ::= { blade4InsDIMMSlotTable 1 }

blade4InsDIMMSlotIndex    OBJECT-TYPE
    SYNTAX    Integer32
    MAX-ACCESS    read-only
    STATUS    current
    DESCRIPTION    "This shows the index of DIMM slot of server blade4."
    ::= { blade4InsDIMMSlotEntry 1 }

blade4InsDIMMSlotExist    OBJECT-TYPE
    SYNTAX    INTEGER {
    non-exist(1), exist(2), unknown(3)
    }
    MAX-ACCESS    read-only
    STATUS    current
    DESCRIPTION    "This shows the registrated state of DIMM slot of server blade4."
    ::= { blade4InsDIMMSlotEntry 2 }

blade4InsDIMMSlotDIMMCapacity    OBJECT-TYPE
    SYNTAX    Integer32
    UNITS    "GB"
    MAX-ACCESS    read-only
    STATUS    current
    DESCRIPTION    "This shows the capacity of DIMM slots of server blade4."
    ::= { blade4InsDIMMSlotEntry 3 }

blade4InsDIMMSlotDIMMType    OBJECT-TYPE
    SYNTAX    DisplayString 
    MAX-ACCESS    read-only
    STATUS    current
    DESCRIPTION    "This shows the DIMM type of DIMM slot of server blade4."
    ::= { blade4InsDIMMSlotEntry 4 }

blade4InsDIMMSlotDIMMFrequency    OBJECT-TYPE
    SYNTAX    Integer32
    UNITS    "MHz"
    MAX-ACCESS    read-only
    STATUS    current
    DESCRIPTION    "This shows the DIMM frequency of DIMM slot of server blade4."
    ::= { blade4InsDIMMSlotEntry 5 }

blade4InsDIMMSlotDIMMCasLatency    OBJECT-TYPE
    SYNTAX    Integer32
    MAX-ACCESS    read-only
    STATUS    current
    DESCRIPTION    "This shows the DIMM cas latency of DIMM slot of server blade4."
    ::= { blade4InsDIMMSlotEntry 6 }

blade4InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade4."
    ::= { blade4InsDIMMSlotEntry 7 }

Blade4InsDIMMSlotEntry ::= SEQUENCE {
    blade4InsDIMMSlotIndex
        Integer32,
    blade4InsDIMMSlotExist
        INTEGER,
    blade4InsDIMMSlotDIMMCapacity
        Integer32,
    blade4InsDIMMSlotDIMMType
        DisplayString,
    blade4InsDIMMSlotDIMMFrequency
        Integer32,
    blade4InsDIMMSlotDIMMCasLatency
        Integer32,
    blade4InsDIMMSlotDIMMStatus
        INTEGER
}

blade4InsPCISlotTable    OBJECT-TYPE
    SYNTAX SEQUENCE OF blade4InsPCISlotEntry
    MAX-ACCESS not-accessible
    STATUS     current
    DESCRIPTION "This shows the table of PCI slot of server blade4."
    ::= { blade4Install 4 }

blade4InsPCISlotEntry    OBJECT-TYPE
    SYNTAX Blade4InsPCISlotEntry
    MAX-ACCESS not-accessible
    STATUS    current
    DESCRIPTION "This shows the entry of PCI slot of server blade4."
    INDEX { blade4InsPCISlotIndex }
    ::= { blade4InsPCISlotTable 1 }

blade4InsPCISlotIndex    OBJECT-TYPE
    SYNTAX    Integer32
    MAX-ACCESS    read-only
    STATUS    current
    DESCRIPTION    "This shows the index of PCI slot of server blade4."
    ::= { blade4InsPCISlotEntry 1 }

blade4InsPCISlotType    OBJECT-TYPE
    SYNTAX    DisplayString 
    MAX-ACCESS    read-only
    STATUS    current
    DESCRIPTION    "This shows the type of PCI slot of server blade4."
    ::= { blade4InsPCISlotEntry 2 }

blade4InsPCISlotExist    OBJECT-TYPE
    SYNTAX    INTEGER {
    non-exist(1), exist(2), unknown(3)
    }
    MAX-ACCESS    read-only
    STATUS    current
    DESCRIPTION    "This shows the registrated state of PCI slot of server blade4."
    ::= { blade4InsPCISlotEntry 3 }

blade4InsPCISlotPCIType    OBJECT-TYPE
    SYNTAX    DisplayString 
    MAX-ACCESS    read-only
    STATUS    current
    DESCRIPTION    "This shows the PCI type of PCI slot of server blade4."
    ::= { blade4InsPCISlotEntry 4 }

blade4InsPCISlotPCIProductName    OBJECT-TYPE
    SYNTAX    DisplayString 
    MAX-ACCESS    read-only
    STATUS    current
    DESCRIPTION    "This shows the PCI product name of PCI slot of server blade4."
    ::= { blade4InsPCISlotEntry 5 }

blade4InsPCISlotPCISerial    OBJECT-TYPE
    SYNTAX    DisplayString 
    MAX-ACCESS    read-only
    STATUS    current
    DESCRIPTION    "This shows the serial number of PCI slot of server blade4."
    ::= { blade4InsPCISlotEntry 6 }

blade4InsPCISlotPCIManufacturer    OBJECT-TYPE
    SYNTAX    DisplayString 
    MAX-ACCESS    read-only
    STATUS    current
    DESCRIPTION    "This shows the manufacturer of PCI slot of server blade4."
    ::= { blade4InsPCISlotEntry 7 }

blade4InsPCISlotNum    OBJECT-TYPE
    SYNTAX    Integer32
    MAX-ACCESS    read-only
    STATUS    current
    DESCRIPTION    "This shows the number of PCI slots of server blade4."
    ::= { blade4InsPCISlotEntry 8 }

Blade4InsPCISlotEntry ::= SEQUENCE {
    blade4InsPCISlotIndex
        Integer32,
    blade4InsPCISlotType
        DisplayString,
    blade4InsPCISlotExist
        INTEGER,
    blade4InsPCISlotPCIType
        DisplayString,
    blade4InsPCISlotPCIProductName
        DisplayString,
    blade4InsPCISlotPCISerial
        DisplayString,
    blade4InsPCISlotPCIManufacturer
        DisplayString,
    blade4InsPCISlotNum
        Integer32
}

blade4InsLOMTable    OBJECT-TYPE
    SYNTAX SEQUENCE OF blade4InsLOMEntry
    MAX-ACCESS not-accessible
    STATUS     current
    DESCRIPTION "This shows the table of onboard LAN of server blade4."
    ::= { blade4Install 5 }

blade4InsLOMEntry    OBJECT-TYPE
    SYNTAX Blade4InsLOMEntry
    MAX-ACCESS not-accessible
    STATUS    current
    DESCRIPTION "This shows the entry of onboard LAN of server blade4."
    INDEX { blade4InsLOMIndex }
    ::= { blade4InsLOMTable 1 }

blade4InsLOMIndex    OBJECT-TYPE
    SYNTAX    Integer32
    MAX-ACCESS    read-only
    STATUS    current
    DESCRIPTION    "This shows the index of onboard LAN of server blade4."
    ::= { blade4InsLOMEntry 1 }

blade4InsLOMType    OBJECT-TYPE
    SYNTAX    DisplayString 
    MAX-ACCESS    read-only
    STATUS    current
    DESCRIPTION    "This shows the type of onboard LAN of server blade4."
    ::= { blade4InsLOMEntry 2 }

blade4InsLOMLinkSpeed    OBJECT-TYPE
    SYNTAX    Integer32
    UNITS    "bps"
    MAX-ACCESS    read-only
    STATUS    current
    DESCRIPTION    "This shows the link speed of onboard LAN of server blade4."
    ::= { blade4InsLOMEntry 3 }

blade4InsLOMMAC    OBJECT-TYPE
    SYNTAX    DisplayString 
    MAX-ACCESS    read-only
    STATUS    current
    DESCRIPTION    "This shows the MAC address of onboard LAN of server blade4."
    ::= { blade4InsLOMEntry 4 }

blade4InsLOMLinkStatus    OBJECT-TYPE
    SYNTAX    INTEGER {
    up (1),down (2),unknown (3)
    }
    MAX-ACCESS    read-only
    STATUS    current
    DESCRIPTION    "This shows the link state of onboard LAN of server blade4."
    ::= { blade4InsLOMEntry 5 }

blade4InsLOMPortDivide    OBJECT-TYPE
    SYNTAX    INTEGER {
    possible (1),Impossible (2),unknown (3)
    }
    MAX-ACCESS    read-only
    STATUS    current
    DESCRIPTION    "This shows the port divide propriety of onboard LAN of server blade4."
    ::= { blade4InsLOMEntry 6 }

blade4InsLOMPortDivideNum    OBJECT-TYPE
    SYNTAX    Integer32
    MAX-ACCESS    read-only
    STATUS    current
    DESCRIPTION    "This shows the port divide number of onboard LAN of server blade4."
    ::= { blade4InsLOMEntry 7 }

Blade4InsLOMEntry ::= SEQUENCE {
    blade4InsLOMIndex
        Integer32,
    blade4InsLOMType
        DisplayString,
    blade4InsLOMLinkSpeed
        Integer32,
    blade4InsLOMMAC
        DisplayString,
    blade4InsLOMLinkStatus
        INTEGER,
    blade4InsLOMPortDivide
        INTEGER,
    blade4InsLOMPortDivideNum
        Integer32
}

blade4HDDSlotTable    OBJECT-TYPE
    SYNTAX SEQUENCE OF blade4HDDSlotEntry
    MAX-ACCESS not-accessible
    STATUS     current
    DESCRIPTION "This shows the table of HDD slot of server blade4."
    ::= { blade4Install 7 }

blade4HDDSlotEntry    OBJECT-TYPE
    SYNTAX Blade4HDDSlotEntry
    MAX-ACCESS not-accessible
    STATUS    current
    DESCRIPTION "This shows the entry of HDD slot of server blade4."
    INDEX { blade4HDDSlotIndex }
    ::= { blade4HDDSlotTable 1 }

blade4HDDSlotIndex    OBJECT-TYPE
    SYNTAX    Integer32
    MAX-ACCESS    read-only
    STATUS    current
    DESCRIPTION    "This shows the index of HDD slot of server blade4."
    ::= { blade4HDDSlotEntry 1 }

blade4HDDSlotNum    OBJECT-TYPE
    SYNTAX    Integer32
    MAX-ACCESS    read-only
    STATUS    current
    DESCRIPTION    "This shows the number of HDD slots of server blade4."
    ::= { blade4HDDSlotEntry 2 }

blade4HDDSlotExist    OBJECT-TYPE
    SYNTAX    INTEGER {
    non-exist(1), exist(2), unknown(3)
    }
    MAX-ACCESS    read-only
    STATUS    current
    DESCRIPTION    "This shows the registrated state of HDD slot of server blade4."
    ::= { blade4HDDSlotEntry 3 }

blade4HDDSlotHDDType    OBJECT-TYPE
    SYNTAX    DisplayString 
    MAX-ACCESS    read-only
    STATUS    current
    DESCRIPTION    "This shows the HDD type of HDD slot of server blade4."
    ::= { blade4HDDSlotEntry 4 }

blade4HDDSlotHDDProductName    OBJECT-TYPE
    SYNTAX    DisplayString 
    MAX-ACCESS    read-only
    STATUS    current
    DESCRIPTION    "This shows the HDD product name of HDD slot of server blade4."
    ::= { blade4HDDSlotEntry 5 }

blade4HDDSlotHDDModel    OBJECT-TYPE
    SYNTAX    DisplayString 
    MAX-ACCESS    read-only
    STATUS    current
    DESCRIPTION    "This shows the HDD model of HDD slot of server blade4."
    ::= { blade4HDDSlotEntry 6 }

blade4HDDSlotHDDSerialNum    OBJECT-TYPE
    SYNTAX    DisplayString 
    MAX-ACCESS    read-only
    STATUS    current
    DESCRIPTION    "This shows the HDD serial number of HDD slot of server blade4."
    ::= { blade4HDDSlotEntry 7 }

blade4HDDSlotHDDCapacity    OBJECT-TYPE
    SYNTAX    Integer32
    UNITS    "GB"
    MAX-ACCESS    read-only
    STATUS    current
    DESCRIPTION    "This shows the HDD capacity of HDD slots of server blade4."
    ::= { blade4HDDSlotEntry 8 }

blade4HDDSlotHDDRPM    OBJECT-TYPE
    SYNTAX    Integer32
    UNITS    "rpm"
    MAX-ACCESS    read-only
    STATUS    current
    DESCRIPTION    "This shows the HDD drive speed of HDD slot of server blade4."
    ::= { blade4HDDSlotEntry 9 }

blade4HDDSlotHDDStatePower    OBJECT-TYPE
    SYNTAX    INTEGER {
    poweroff (1), poweron (2), unknown (3)
    }
    MAX-ACCESS    read-only
    STATUS    current
    DESCRIPTION    "This shows the HDD power supply state of HDD slot of server blade4."
    ::= { blade4HDDSlotEntry 10 }

blade4HDDSlotHDDStateHealth    OBJECT-TYPE
    SYNTAX    INTEGER {
    normal (1),fail (2),unknown (3),rebuild (4)
    }
    MAX-ACCESS    read-only
    STATUS    current
    DESCRIPTION    "This shows the HDD health state of HDD slot of server blade4."
    ::= { blade4HDDSlotEntry 11 }

blade4HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade4(activity)."
    ::= { blade4HDDSlotEntry 12 }

blade4HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade4(status)."
    ::= { blade4HDDSlotEntry 13 }

blade4HDDSlotHDDFWInfoName    OBJECT-TYPE
    SYNTAX    DisplayString 
    MAX-ACCESS    read-only
    STATUS    current
    DESCRIPTION    "This shows the HDD firmware name of HDD slot of server blade4."
    ::= { blade4HDDSlotEntry 20 }

blade4HDDSlotHDDFWInfoCurrentVer    OBJECT-TYPE
    SYNTAX    DisplayString 
    MAX-ACCESS    read-only
    STATUS    current
    DESCRIPTION    "This shows the HDD firmware current version of HDD slot of server blade4."
    ::= { blade4HDDSlotEntry 21 }

blade4HDDSlotHDDFWInfoNextVer    OBJECT-TYPE
    SYNTAX    DisplayString 
    MAX-ACCESS    read-only
    STATUS    current
    DESCRIPTION    "This shows the HDD firmware next version of HDD slot of server blade4."
    ::= { blade4HDDSlotEntry 22 }

Blade4HDDSlotEntry ::= SEQUENCE {
    blade4HDDSlotIndex
        Integer32,
    blade4HDDSlotNum
        Integer32,
    blade4HDDSlotExist
        INTEGER,
    blade4HDDSlotHDDType
        DisplayString,
    blade4HDDSlotHDDProductName
        DisplayString,
    blade4HDDSlotHDDModel
        DisplayString,
    blade4HDDSlotHDDSerialNum
        DisplayString,
    blade4HDDSlotHDDCapacity
        Integer32,
    blade4HDDSlotHDDRPM
        Integer32,
    blade4HDDSlotHDDStatePower
        INTEGER,
    blade4HDDSlotHDDStateHealth
        INTEGER,
    blade4HDDSlotHDDStateLEDACT
        INTEGER,
    blade4HDDSlotHDDStateLEDSTS
        INTEGER,
    blade4HDDSlotHDDFWInfoName
        DisplayString,
    blade4HDDSlotHDDFWInfoCurrentVer
        DisplayString,
    blade4HDDSlotHDDFWInfoNextVer
        DisplayString
}

blade4ExpansionHDDSlotTable    OBJECT-TYPE
    SYNTAX SEQUENCE OF blade4ExpansionHDDSlotEntry
    MAX-ACCESS not-accessible
    STATUS     current
    DESCRIPTION "This shows the table of expansion HDD slot of server blade4."
    ::= { blade4Install 8 }

blade4ExpansionHDDSlotEntry    OBJECT-TYPE
    SYNTAX Blade4ExpansionHDDSlotEntry
    MAX-ACCESS not-accessible
    STATUS    current
    DESCRIPTION "This shows the entry of expansion HDD slot of server blade4."
    INDEX { blade4ExpansionHDDSlotIndex }
    ::= { blade4ExpansionHDDSlotTable 1 }

blade4ExpansionHDDSlotIndex    OBJECT-TYPE
    SYNTAX    Integer32
    MAX-ACCESS    read-only
    STATUS    current
    DESCRIPTION    "This shows the index of expansion HDD slot of server blade4."
    ::= { blade4ExpansionHDDSlotEntry 1 }

blade4ExpansionHDDSlotNum    OBJECT-TYPE
    SYNTAX    Integer32
    MAX-ACCESS    read-only
    STATUS    current
    DESCRIPTION    "This shows the number of expansion HDD slots of server blade4."
    ::= { blade4ExpansionHDDSlotEntry 2 }

blade4ExpansionHDDSlotExist    OBJECT-TYPE
    SYNTAX    INTEGER {
    non-exist(1), exist(2), unknown(3)
    }
    MAX-ACCESS    read-only
    STATUS    current
    DESCRIPTION    "This shows the registrated state of expansion HDD slot of server blade4."
    ::= { blade4ExpansionHDDSlotEntry 3 }

blade4ExpansionHDDSlotHDDType    OBJECT-TYPE
    SYNTAX    DisplayString 
    MAX-ACCESS    read-only
    STATUS    current
    DESCRIPTION    "This shows the HDD type of expansion HDD slot of server blade4."
    ::= { blade4ExpansionHDDSlotEntry 4 }

blade4ExpansionHDDSlotHDDProductName    OBJECT-TYPE
    SYNTAX    DisplayString 
    MAX-ACCESS    read-only
    STATUS    current
    DESCRIPTION    "This shows the HDD product name of expansion HDD slot of server blade4."
    ::= { blade4ExpansionHDDSlotEntry 5 }

blade4ExpansionHDDSlotHDDModel    OBJECT-TYPE
    SYNTAX    DisplayString 
    MAX-ACCESS    read-only
    STATUS    current
    DESCRIPTION    "This shows the HDD model of expansion HDD slot of server blade4."
    ::= { blade4ExpansionHDDSlotEntry 6 }

blade4ExpansionHDDSlotHDDSerialNum    OBJECT-TYPE
    SYNTAX    DisplayString 
    MAX-ACCESS    read-only
    STATUS    current
    DESCRIPTION    "This shows the HDD serial number of expansion HDD slot of server blade4."
    ::= { blade4ExpansionHDDSlotEntry 7 }

blade4ExpansionHDDSlotHDDCapacity    OBJECT-TYPE
    SYNTAX    Integer32
    UNITS    "GB"
    MAX-ACCESS    read-only
    STATUS    current
    DESCRIPTION    "This shows the HDD capacity of expansion HDD slots of server blade4."
    ::= { blade4ExpansionHDDSlotEntry 8 }

blade4ExpansionHDDSlotHDDRPM    OBJECT-TYPE
    SYNTAX    Integer32
    UNITS    "rpm"
    MAX-ACCESS    read-only
    STATUS    current
    DESCRIPTION    "This shows the HDD drive speed of expansion HDD slot of server blade4."
    ::= { blade4ExpansionHDDSlotEntry 9 }

blade4ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade4."
    ::= { blade4ExpansionHDDSlotEntry 10 }

blade4ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade4."
    ::= { blade4ExpansionHDDSlotEntry 11 }

blade4ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade4(activity)."
    ::= { blade4ExpansionHDDSlotEntry 12 }

blade4ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade4(status)."
    ::= { blade4ExpansionHDDSlotEntry 13 }

blade4ExpansionHDDSlotHDDFWInfoName    OBJECT-TYPE
    SYNTAX    DisplayString 
    MAX-ACCESS    read-only
    STATUS    current
    DESCRIPTION    "This shows the HDD firmware name of expansion HDD slot of server blade4."
    ::= { blade4ExpansionHDDSlotEntry 20 }

blade4ExpansionHDDSlotHDDFWInfoCurrentVer    OBJECT-TYPE
    SYNTAX    DisplayString 
    MAX-ACCESS    read-only
    STATUS    current
    DESCRIPTION    "This shows the HDD firmware current version of expansion HDD slot of server blade4."
    ::= { blade4ExpansionHDDSlotEntry 21 }

blade4ExpansionHDDSlotHDDFWInfoNextVer    OBJECT-TYPE
    SYNTAX    DisplayString 
    MAX-ACCESS    read-only
    STATUS    current
    DESCRIPTION    "This shows the HDD firmware next version of expansion HDD slot of server blade4."
    ::= { blade4ExpansionHDDSlotEntry 22 }

Blade4ExpansionHDDSlotEntry ::= SEQUENCE {
    blade4ExpansionHDDSlotIndex
        Integer32,
    blade4ExpansionHDDSlotNum
        Integer32,
    blade4ExpansionHDDSlotExist
        INTEGER,
    blade4ExpansionHDDSlotHDDType
        DisplayString,
    blade4ExpansionHDDSlotHDDProductName
        DisplayString,
    blade4ExpansionHDDSlotHDDModel
        DisplayString,
    blade4ExpansionHDDSlotHDDSerialNum
        DisplayString,
    blade4ExpansionHDDSlotHDDCapacity
        Integer32,
    blade4ExpansionHDDSlotHDDRPM
        Integer32,
    blade4ExpansionHDDSlotHDDStatePower
        INTEGER,
    blade4ExpansionHDDSlotHDDStateHealth
        INTEGER,
    blade4ExpansionHDDSlotHDDStateLEDACT
        INTEGER,
    blade4ExpansionHDDSlotHDDStateLEDSTS
        INTEGER,
    blade4ExpansionHDDSlotHDDFWInfoName
        DisplayString,
    blade4ExpansionHDDSlotHDDFWInfoCurrentVer
        DisplayString,
    blade4ExpansionHDDSlotHDDFWInfoNextVer
        DisplayString
}

blade4VoltageSensorTable    OBJECT-TYPE
    SYNTAX SEQUENCE OF blade4VoltageSensorEntry
    MAX-ACCESS not-accessible
    STATUS     current
    DESCRIPTION "This shows the table of voltage sensor of server blade4."
    ::= { blade4State 40 }

blade4VoltageSensorEntry    OBJECT-TYPE
    SYNTAX Blade4VoltageSensorEntry
    MAX-ACCESS not-accessible
    STATUS    current
    DESCRIPTION "This shows the entry of voltage sensor of server blade4."
    INDEX { blade4VoltageSensorIndex }
    ::= { blade4VoltageSensorTable 1 }

blade4VoltageSensorIndex    OBJECT-TYPE
    SYNTAX    Integer32
    MAX-ACCESS    read-only
    STATUS    current
    DESCRIPTION    "This shows the index of voltage sensor of server blade4."
    ::= { blade4VoltageSensorEntry 1 }

blade4VoltageSensorName    OBJECT-TYPE
    SYNTAX    DisplayString 
    MAX-ACCESS    read-only
    STATUS    current
    DESCRIPTION    "This shows the voltage sensor name of server blade4."
    ::= { blade4VoltageSensorEntry 2 }

blade4VoltageSensorValue    OBJECT-TYPE
    SYNTAX    Integer32
    UNITS    "0.1 V"
    MAX-ACCESS    read-only
    STATUS    current
    DESCRIPTION    "This shows the voltage sensor value of server blade4."
    ::= { blade4VoltageSensorEntry 3 }

blade4VoltageSensorValid    OBJECT-TYPE
    SYNTAX    INTEGER {
    invalid (1),valid (2),unknown (3)
    }
    MAX-ACCESS    read-only
    STATUS    current
    DESCRIPTION    "This shows the validity of voltage sensor value of server blade4."
    ::= { blade4VoltageSensorEntry 4 }

Blade4VoltageSensorEntry ::= SEQUENCE {
    blade4VoltageSensorIndex
        Integer32,
    blade4VoltageSensorName
        DisplayString,
    blade4VoltageSensorValue
        Integer32,
    blade4VoltageSensorValid
        INTEGER
}

blade4TempSensorTable    OBJECT-TYPE
    SYNTAX SEQUENCE OF blade4TempSensorEntry
    MAX-ACCESS not-accessible
    STATUS     current
    DESCRIPTION "This shows the table of temperature sensor of server blade4."
    ::= { blade4State 41 }

blade4TempSensorEntry    OBJECT-TYPE
    SYNTAX Blade4TempSensorEntry
    MAX-ACCESS not-accessible
    STATUS    current
    DESCRIPTION "This shows the entry of temperature sensor of server blade4."
    INDEX { blade4TempSensorIndex }
    ::= { blade4TempSensorTable 1 }

blade4TempSensorIndex    OBJECT-TYPE
    SYNTAX    Integer32
    MAX-ACCESS    read-only
    STATUS    current
    DESCRIPTION    "This shows the index of temperature sensor of server blade4."
    ::= { blade4TempSensorEntry 1 }

blade4TempSensorName    OBJECT-TYPE
    SYNTAX    DisplayString 
    MAX-ACCESS    read-only
    STATUS    current
    DESCRIPTION    "This shows the temperature sensor name of server blade4."
    ::= { blade4TempSensorEntry 2 }

blade4TempSensorValue    OBJECT-TYPE
    SYNTAX    Integer32
    UNITS    "0.1 degrees C"
    MAX-ACCESS    read-only
    STATUS    current
    DESCRIPTION    "This shows the temperature sensor value of server blade4."
    ::= { blade4TempSensorEntry 3 }

blade4TempSensorValid    OBJECT-TYPE
    SYNTAX    INTEGER {
    invalid (1),valid (2),unknown (3)
    }
    MAX-ACCESS    read-only
    STATUS    current
    DESCRIPTION    "This shows the validity of temperature sensor value of server blade4."
    ::= { blade4TempSensorEntry 4 }

Blade4TempSensorEntry ::= SEQUENCE {
    blade4TempSensorIndex
        Integer32,
    blade4TempSensorName
        DisplayString,
    blade4TempSensorValue
        Integer32,
    blade4TempSensorValid
        INTEGER
}

blade4FWInfo    OBJECT IDENTIFIER ::= { blade4 5 } 

blade4FWInfoTotalCurrentVer    OBJECT-TYPE
    SYNTAX    DisplayString (SIZE(0..40))
    MAX-ACCESS    read-only
    STATUS    current
    DESCRIPTION    "This shows the total current version of firmware of server blade4."
    ::= { blade4FWInfo 1 }

blade4FWInfoTotalNextVer    OBJECT-TYPE
    SYNTAX    DisplayString (SIZE(0..40))
    MAX-ACCESS    read-only
    STATUS    current
    DESCRIPTION    "This shows the total next version of firmware of server blade4."
    ::= { blade4FWInfo 2 }

blade4FWInfoTable    OBJECT-TYPE
    SYNTAX SEQUENCE OF blade4FWInfoEntry
    MAX-ACCESS not-accessible
    STATUS     current
    DESCRIPTION "This shows the table of firmware information of server blade4."
    ::= { blade4FWInfo 3 }

blade4FWInfoEntry    OBJECT-TYPE
    SYNTAX Blade4FWInfoEntry
    MAX-ACCESS not-accessible
    STATUS    current
    DESCRIPTION "This shows the entry of firmware information of server blade4."
    INDEX { blade4FWInfoIndex }
    ::= { blade4FWInfoTable 1 }

blade4FWInfoIndex    OBJECT-TYPE
    SYNTAX    Integer32
    MAX-ACCESS    read-only
    STATUS    current
    DESCRIPTION    "This shows the index of firmware information of server blade4."
    ::= { blade4FWInfoEntry 1 }

blade4FWInfoName    OBJECT-TYPE
    SYNTAX    DisplayString (SIZE(0..40))
    MAX-ACCESS    read-only
    STATUS    current
    DESCRIPTION    "This shows the firmware name of server blade4."
    ::= { blade4FWInfoEntry 2 }

blade4FWCurrentVer    OBJECT-TYPE
    SYNTAX    DisplayString (SIZE(0..40))
    MAX-ACCESS    read-only
    STATUS    current
    DESCRIPTION    "This shows the firmware current version of server blade4."
    ::= { blade4FWInfoEntry 3 }

blade4FWInfoNextVer    OBJECT-TYPE
    SYNTAX    DisplayString (SIZE(0..40))
    MAX-ACCESS    read-only
    STATUS    current
    DESCRIPTION    "This shows the firmware next version of server blade4."
    ::= { blade4FWInfoEntry 4 }

blade4FWInfoHVMCurrentVer    OBJECT-TYPE
    SYNTAX    DisplayString (SIZE(0..40))
    MAX-ACCESS    read-only
    STATUS    current
    DESCRIPTION    "This shows the HVM current version of server blade4."
    ::= { blade4FWInfo 4 }

blade4FWInfoHVMNextVer    OBJECT-TYPE
    SYNTAX    DisplayString (SIZE(0..40))
    MAX-ACCESS    read-only
    STATUS    current
    DESCRIPTION    "This shows the HVM next version of server blade4."
    ::= { blade4FWInfo 5 }

Blade4FWInfoEntry ::= SEQUENCE {
    blade4FWInfoIndex
        Integer32,
    blade4FWInfoName
        DisplayString,
    blade4FWCurrentVer
        DisplayString,
    blade4FWInfoNextVer
        DisplayString,
    blade4FWInfoHVMCurrentVer
        DisplayString,
    blade4FWInfoHVMNextVer
        DisplayString
}

blade5    OBJECT IDENTIFIER ::= { blade 5 } 

blade5BasicInfo    OBJECT IDENTIFIER ::= { blade5 1 } 

blade5InfoProductName    OBJECT-TYPE
    SYNTAX    DisplayString (SIZE(0..40))
    MAX-ACCESS    read-only
    STATUS    current
    DESCRIPTION    "This shows the product name of server blade5."
    ::= { blade5BasicInfo 1 }

blade5InfoModel    OBJECT-TYPE
    SYNTAX    DisplayString (SIZE(0..40))
    MAX-ACCESS    read-only
    STATUS    current
    DESCRIPTION    "This shows the model name of server blade5."
    ::= { blade5BasicInfo 2 }

blade5InfoSerialNum    OBJECT-TYPE
    SYNTAX    DisplayString (SIZE(0..40))
    MAX-ACCESS    read-only
    STATUS    current
    DESCRIPTION    "This shows the serial number of server blade5."
    ::= { blade5BasicInfo 3 }

blade5InfoProductVersion    OBJECT-TYPE
    SYNTAX    DisplayString (SIZE(0..40))
    MAX-ACCESS    read-only
    STATUS    current
    DESCRIPTION    "This shows the product version of server blade5."
    ::= { blade5BasicInfo 4 }

blade5InfoProductManufacturer    OBJECT-TYPE
    SYNTAX    DisplayString (SIZE(0..40))
    MAX-ACCESS    read-only
    STATUS    current
    DESCRIPTION    "This shows the product manufacturer of server blade5."
    ::= { blade5BasicInfo 5 }

blade5InfoBoardProductName    OBJECT-TYPE
    SYNTAX    DisplayString (SIZE(0..40))
    MAX-ACCESS    read-only
    STATUS    current
    DESCRIPTION    "This shows the board product name of server blade5."
    ::= { blade5BasicInfo 7 }

blade5InfoBoardSerialNum    OBJECT-TYPE
    SYNTAX    DisplayString (SIZE(0..40))
    MAX-ACCESS    read-only
    STATUS    current
    DESCRIPTION    "This shows the board serial number of server blade5."
    ::= { blade5BasicInfo 8 }

blade5InfoBoardManufacturer    OBJECT-TYPE
    SYNTAX    DisplayString (SIZE(0..40))
    MAX-ACCESS    read-only
    STATUS    current
    DESCRIPTION    "This shows the board manufacturer of server blade5."
    ::= { blade5BasicInfo 9 }

blade5InfoUUID    OBJECT-TYPE
    SYNTAX    DisplayString (SIZE(0..40))
    MAX-ACCESS    read-only
    STATUS    current
    DESCRIPTION    "This shows UUID(universal Unique ID) of server blade5."
    ::= { blade5BasicInfo 10 }

blade5InfoLogicalPartitionSupport    OBJECT-TYPE
    SYNTAX    INTEGER {
    not-support(1), support(2),unknown(3)
    }
    MAX-ACCESS    read-only
    STATUS    current
    DESCRIPTION    "This shows whether the server blade5 supports HVM or not of server blade1."
    ::= { blade5BasicInfo 11 }

blade5InfoRemoteKVMSupport    OBJECT-TYPE
    SYNTAX    INTEGER {
    not-support(1), support(2),unknown(3)
    }
    MAX-ACCESS    read-only
    STATUS    current
    DESCRIPTION    "This shows whether the server blade5 supports remote KVM or not of server blade1."
    ::= { blade5BasicInfo 12 }

blade5InfoSpec    OBJECT IDENTIFIER ::= { blade5BasicInfo 20 } 

blade5SpecInputCurrentType    OBJECT-TYPE
    SYNTAX    INTEGER {
    ac(1),dc(2),unknown(3)
    }
    MAX-ACCESS    read-only
    STATUS    current
    DESCRIPTION    "This shows the currency type of server blade5."
    ::= { blade5InfoSpec 1 }

blade5SpecRateVoltage    OBJECT-TYPE
    SYNTAX    Integer32
    UNITS    "0.1 V"
    MAX-ACCESS    read-only
    STATUS    current
    DESCRIPTION    "This shows the rated voltage of server blade5."
    ::= { blade5InfoSpec 2 }

blade5SpecConsumptionCurrent    OBJECT-TYPE
    SYNTAX    Integer32
    UNITS    "0.1 A"
    MAX-ACCESS    read-only
    STATUS    current
    DESCRIPTION    "This shows the consumption current of server blade5."
    ::= { blade5InfoSpec 3 }

blade5SpecPowerConsumption    OBJECT-TYPE
    SYNTAX    Integer32
    UNITS    "W"
    MAX-ACCESS    read-only
    STATUS    current
    DESCRIPTION    "This shows the power consumption of server blade5."
    ::= { blade5InfoSpec 4 }

blade5SpecMass    OBJECT-TYPE
    SYNTAX    Integer32
    UNITS    "0.1 kg"
    MAX-ACCESS    read-only
    STATUS    current
    DESCRIPTION    "This shows the weight of server blade5."
    ::= { blade5InfoSpec 5 }

blade5InfoUpperLimitIntakeTemp    OBJECT-TYPE
    SYNTAX    Integer32
    UNITS    "0.1 degrees C"
    MAX-ACCESS    read-only
    STATUS    current
    DESCRIPTION    "This shows the maximum limited intake temperature of server blade5."
    ::= { blade5InfoSpec 6 }

blade5InfoLowerLimitIntakeTemp    OBJECT-TYPE
    SYNTAX    Integer32
    UNITS    "0.1 degrees C"
    MAX-ACCESS    read-only
    STATUS    current
    DESCRIPTION    "This shows the minimum limited intake temperature of server blade5."
    ::= { blade5InfoSpec 7 }

blade5SpecSize    OBJECT-TYPE
    SYNTAX    DisplayString (SIZE(0..40))
    MAX-ACCESS    read-only
    STATUS    current
    DESCRIPTION    "This shows the size of server blade5."
    ::= { blade5InfoSpec 8 }

blade5SpecOccupySlots    OBJECT-TYPE
    SYNTAX    Integer32
    MAX-ACCESS    read-only
    STATUS    current
    DESCRIPTION    "This shows the dedicated number of slots of server blade5."
    ::= { blade5InfoSpec 9 }

blade5SpecExpansionBladeSlot    OBJECT-TYPE
    SYNTAX    Integer32
    MAX-ACCESS    read-only
    STATUS    current
    DESCRIPTION    "This shows the number of slots of expansion blade of server blade5."
    ::= { blade5InfoSpec 10 }

blade5InfoExpansionBladeTable    OBJECT-TYPE
    SYNTAX SEQUENCE OF blade5InfoExpansionBladeEntry
    MAX-ACCESS not-accessible
    STATUS     current
    DESCRIPTION "This shows the table of expansion blade slot of server blade5."
    ::= { blade5BasicInfo 30 }

blade5InfoExpansionBladeEntry    OBJECT-TYPE
    SYNTAX Blade5InfoExpansionBladeEntry
    MAX-ACCESS not-accessible
    STATUS    current
    DESCRIPTION "This shows the entry of expansion blade slot of server blade5."
    INDEX { blade5InfoExpansionBladeIndex }
    ::= { blade5InfoExpansionBladeTable 1 }

blade5InfoExpansionBladeIndex    OBJECT-TYPE
    SYNTAX    Integer32
    MAX-ACCESS    read-only
    STATUS    current
    DESCRIPTION    "This shows the index of expansion blade slot of server blade5."
    ::= { blade5InfoExpansionBladeEntry 1 }

blade5InfoExpansionBladeExist    OBJECT-TYPE
    SYNTAX    INTEGER {
    non-exist(1), exist(2), unknown(3)
    }
    MAX-ACCESS    read-only
    STATUS    current
    DESCRIPTION    "This shows the registrated state of expansion blade of server blade5."
    ::= { blade5InfoExpansionBladeEntry 2 }

blade5InfoExpansionBladeProductName    OBJECT-TYPE
    SYNTAX    DisplayString (SIZE(0..40))
    MAX-ACCESS    read-only
    STATUS    current
    DESCRIPTION    "This shows the product name of expansion blade of server blade5."
    ::= { blade5InfoExpansionBladeEntry 3 }

blade5InfoExpansionBladeModel    OBJECT-TYPE
    SYNTAX    DisplayString (SIZE(0..40))
    MAX-ACCESS    read-only
    STATUS    current
    DESCRIPTION    "This shows the model name of expansion blade of server blade5."
    ::= { blade5InfoExpansionBladeEntry 4 }

blade5InfoExpansionBladeSerialNum    OBJECT-TYPE
    SYNTAX    DisplayString (SIZE(0..40))
    MAX-ACCESS    read-only
    STATUS    current
    DESCRIPTION    "This shows the serial number of expansion blade of server blade5."
    ::= { blade5InfoExpansionBladeEntry 5 }

blade5InfoExpansionBladeProductVersion    OBJECT-TYPE
    SYNTAX    DisplayString (SIZE(0..40))
    MAX-ACCESS    read-only
    STATUS    current
    DESCRIPTION    "This shows the product version of expansion blade of server blade5."
    ::= { blade5InfoExpansionBladeEntry 6 }

blade5InfoExpansionBladeProductManufacturer    OBJECT-TYPE
    SYNTAX    DisplayString (SIZE(0..40))
    MAX-ACCESS    read-only
    STATUS    current
    DESCRIPTION    "This shows the product manufacturer of expansion blade of server blade5."
    ::= { blade5InfoExpansionBladeEntry 7 }

blade5InfoExpansionBladeBoardProductName    OBJECT-TYPE
    SYNTAX    DisplayString (SIZE(0..40))
    MAX-ACCESS    read-only
    STATUS    current
    DESCRIPTION    "This shows the board product name of expansion blade of server blade5."
    ::= { blade5InfoExpansionBladeEntry 9 }

blade5InfoExpansionBladeBoardSerialNum    OBJECT-TYPE
    SYNTAX    DisplayString (SIZE(0..40))
    MAX-ACCESS    read-only
    STATUS    current
    DESCRIPTION    "This shows the board serial number of expansion blade of server blade5."
    ::= { blade5InfoExpansionBladeEntry 10 }

blade5InfoExpansionBladeBoardManufacturer    OBJECT-TYPE
    SYNTAX    DisplayString (SIZE(0..40))
    MAX-ACCESS    read-only
    STATUS    current
    DESCRIPTION    "This shows the board manufacturer of expansion blade of server blade5."
    ::= { blade5InfoExpansionBladeEntry 11 }

Blade5InfoExpansionBladeEntry ::= SEQUENCE {
    blade5InfoExpansionBladeIndex
        Integer32,
    blade5InfoExpansionBladeExist
        INTEGER,
    blade5InfoExpansionBladeProductName
        DisplayString,
    blade5InfoExpansionBladeModel
        DisplayString,
    blade5InfoExpansionBladeSerialNum
        DisplayString,
    blade5InfoExpansionBladeProductVersion
        DisplayString,
    blade5InfoExpansionBladeProductManufacturer
        DisplayString,
    blade5InfoExpansionBladeBoardProductName
        DisplayString,
    blade5InfoExpansionBladeBoardSerialNum
        DisplayString,
    blade5InfoExpansionBladeBoardManufacturer
        DisplayString
}

blade5Capacity    OBJECT IDENTIFIER ::= { blade5 2 } 

blade5CapacityCPUSocket    OBJECT-TYPE
    SYNTAX    Integer32
    MAX-ACCESS    read-only
    STATUS    current
    DESCRIPTION    "This shows the capacity of CPU sockets of server blade5."
    ::= { blade5Capacity 1 }

blade5CapacityDIMMSlot    OBJECT-TYPE
    SYNTAX    Integer32
    MAX-ACCESS    read-only
    STATUS    current
    DESCRIPTION    "This shows the capacity of DIMM slots of server blade5."
    ::= { blade5Capacity 2 }

blade5CapacityPCISlot    OBJECT-TYPE
    SYNTAX    Integer32
    MAX-ACCESS    read-only
    STATUS    current
    DESCRIPTION    "This shows the capacity of PCI slots of server blade5."
    ::= { blade5Capacity 3 }

blade5CapacityLOM    OBJECT-TYPE
    SYNTAX    Integer32
    MAX-ACCESS    read-only
    STATUS    current
    DESCRIPTION    "This shows the capacity of onboard LAN ports of server blade5."
    ::= { blade5Capacity 4 }

blade5CapacityFan    OBJECT-TYPE
    SYNTAX    Integer32
    MAX-ACCESS    read-only
    STATUS    current
    DESCRIPTION    "This shows the capacity of onboard fans of server blade5."
    ::= { blade5Capacity 5 }

blade5CapacityHDDSlot    OBJECT-TYPE
    SYNTAX    Integer32
    MAX-ACCESS    read-only
    STATUS    current
    DESCRIPTION    "This shows the capacity of HDD slots of server blade5."
    ::= { blade5Capacity 6 }

blade5CapacityVoltageSensor    OBJECT-TYPE
    SYNTAX    Integer32
    MAX-ACCESS    read-only
    STATUS    current
    DESCRIPTION    "This shows the capacity of voltage sensors of blade5."
    ::= { blade5Capacity 7 }

blade5CapacityTempSensor    OBJECT-TYPE
    SYNTAX    Integer32
    MAX-ACCESS    read-only
    STATUS    current
    DESCRIPTION    "This shows the capacity of temperature sensors of blade5."
    ::= { blade5Capacity 8 }

blade5CapacityExpansionHDDSlot    OBJECT-TYPE
    SYNTAX    Integer32
    MAX-ACCESS    read-only
    STATUS    current
    DESCRIPTION    "This shows the capacity of expansion HDD slots of server blade5."
    ::= { blade5Capacity 9 }

blade5CapacityLED    OBJECT-TYPE
    SYNTAX    Integer32
    MAX-ACCESS    read-only
    STATUS    current
    DESCRIPTION    "This shows the capacity of count of LEDs of server blade5."
    ::= { blade5Capacity 10 }

blade5Settings    OBJECT IDENTIFIER ::= { blade5 3 } 

blade5SettingsBelongPartitionNum    OBJECT-TYPE
    SYNTAX    Integer32
    MAX-ACCESS    read-only
    STATUS    current
    DESCRIPTION    "This shows the partition number of server blade5."
    ::= { blade5Settings 1 }

blade5SettingsDetailHVMLicenceModel    OBJECT-TYPE
    SYNTAX    DisplayString (SIZE(0..40))
    MAX-ACCESS    read-only
    STATUS    current
    DESCRIPTION    "This shows the HVM licence of detailed server blade5 (model). "
    ::= { blade5Settings 2 }

blade5SettingsDetailHVMLicenceAvailableVersion    OBJECT-TYPE
    SYNTAX    DisplayString (SIZE(0..40))
    MAX-ACCESS    read-only
    STATUS    current
    DESCRIPTION    "This shows the HVM licence of detailed server blade5 (available version). "
    ::= { blade5Settings 3 }

blade5SettingsManagementPortIPAddress    OBJECT-TYPE
    SYNTAX    DisplayString (SIZE(0..40))
    MAX-ACCESS    read-only
    STATUS    current
    DESCRIPTION    "This shows the IP address of management port of server blade5."
    ::= { blade5Settings 4 }

blade5State    OBJECT IDENTIFIER ::= { blade5 4 } 

blade5StateSlotNum    OBJECT-TYPE
    SYNTAX    Integer32
    MAX-ACCESS    read-only
    STATUS    current
    DESCRIPTION    "This shows the number of installed slots of server blade5."
    ::= { blade5State 1 }

blade5StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade5."
    ::= { blade5State 2 }

blade5StateHealth    OBJECT-TYPE
    SYNTAX    INTEGER {
    normal (1),fail (2),unknown (3)
    }
    MAX-ACCESS    read-only
    STATUS    current
    DESCRIPTION    "This shows the health state of server blade5."
    ::= { blade5State 3 }

blade5StatePrimaly    OBJECT-TYPE
    SYNTAX    INTEGER {
    primary(1), non-primary(2),unknown(3)
    }
    MAX-ACCESS    read-only
    STATUS    current
    DESCRIPTION    "This shows the primary state of server blade5."
    ::= { blade5State 4 }

blade5StateCurrentVoltage    OBJECT-TYPE
    SYNTAX    Integer32
    UNITS    "0.1 V"
    MAX-ACCESS    read-only
    STATUS    current
    DESCRIPTION    "This shows the current voltage of server blade5."
    ::= { blade5State 5 }

blade5StateConsumptionCurrent    OBJECT-TYPE
    SYNTAX    Integer32
    UNITS    "0.1 A"
    MAX-ACCESS    read-only
    STATUS    current
    DESCRIPTION    "This shows the consumption current of server blade5."
    ::= { blade5State 6 }

blade5StatePowerConsumption    OBJECT-TYPE
    SYNTAX    Integer32
    UNITS    "W"
    MAX-ACCESS    read-only
    STATUS    current
    DESCRIPTION    "This shows the power consumption of server blade5."
    ::= { blade5State 7 }

blade5StateIntakeTemp    OBJECT-TYPE
    SYNTAX    INTEGER {
    normal (1), higher-warning (2), higher-error (3), lower-warning (4), unknown(5)
    }
    MAX-ACCESS    read-only
    STATUS    current
    DESCRIPTION    "This shows the state of intake temperature of server blade5."
    ::= { blade5State 8 }

blade5StateLEDTable    OBJECT-TYPE
    SYNTAX SEQUENCE OF blade5StateLEDEntry
    MAX-ACCESS not-accessible
    STATUS     current
    DESCRIPTION "This shows the table of LED of server blade5."
    ::= { blade5State 9 }

blade5StateLEDEntry    OBJECT-TYPE
    SYNTAX Blade5StateLEDEntry
    MAX-ACCESS not-accessible
    STATUS    current
    DESCRIPTION "This shows the entry of LED of server blade5."
    INDEX { blade5StateLEDIndex }
    ::= { blade5StateLEDTable 1 }

blade5StateLEDIndex    OBJECT-TYPE
    SYNTAX    Integer32
    MAX-ACCESS    read-only
    STATUS    current
    DESCRIPTION    "This shows the index of LED of server blade5."
    ::= { blade5StateLEDEntry 1 }

blade5StateLEDName    OBJECT-TYPE
    SYNTAX    DisplayString (SIZE(0..40))
    MAX-ACCESS    read-only
    STATUS    current
    DESCRIPTION    "This shows the name of LED of server blade5."
    ::= { blade5StateLEDEntry 2 }

blade5StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade5."
    ::= { blade5StateLEDEntry 3 }

blade5StateLEDColor    OBJECT-TYPE
    SYNTAX    INTEGER {
    blue (1),green (2),red (3),amber (4),unknown (5)
    }
    MAX-ACCESS    read-only
    STATUS    current
    DESCRIPTION    "This shows the color of LED of server blade5."
    ::= { blade5StateLEDEntry 4 }

Blade5StateLEDEntry ::= SEQUENCE {
    blade5StateLEDIndex
        Integer32,
    blade5StateLEDName
        DisplayString,
    blade5StateLEDState
        INTEGER,
    blade5StateLEDColor
        INTEGER
}

blade5StateOther    OBJECT IDENTIFIER ::= { blade5State 20 } 

blade5MaintMode    OBJECT-TYPE
    SYNTAX    INTEGER {
    Normal(1), CE-Maint-mode(2), User-Maint-mode(3), unknown(4)
    }
    MAX-ACCESS    read-only
    STATUS    current
    DESCRIPTION    "This shows the maintenance mode of server blade5."
    ::= { blade5StateOther 1 }

blade5Install    OBJECT IDENTIFIER ::= { blade5State 30 } 

blade5InsCPUSocketTable    OBJECT-TYPE
    SYNTAX SEQUENCE OF blade5InsCPUSocketEntry
    MAX-ACCESS not-accessible
    STATUS     current
    DESCRIPTION "This shows the table of CPU socket of server blade5."
    ::= { blade5Install 1 }

blade5InsCPUSocketEntry    OBJECT-TYPE
    SYNTAX Blade5InsCPUSocketEntry
    MAX-ACCESS not-accessible
    STATUS    current
    DESCRIPTION "This shows the entry of CPU socket of server blade5."
    INDEX { blade5InsCPUSocketIndex }
    ::= { blade5InsCPUSocketTable 1 }

blade5InsCPUSocketIndex    OBJECT-TYPE
    SYNTAX    Integer32
    MAX-ACCESS    read-only
    STATUS    current
    DESCRIPTION    "This shows the index of CPU socket of server blade5."
    ::= { blade5InsCPUSocketEntry 1 }

blade5InsCPUSocketNum    OBJECT-TYPE
    SYNTAX    Integer32
    MAX-ACCESS    read-only
    STATUS    current
    DESCRIPTION    "This shows the number of CPU sockets of server blade5."
    ::= { blade5InsCPUSocketEntry 2 }

blade5InsCPUSocketExist    OBJECT-TYPE
    SYNTAX    INTEGER {
    non-exist(1), exist(2), unknown(3)
    }
    MAX-ACCESS    read-only
    STATUS    current
    DESCRIPTION    "This shows the registrated state of CPU socket of server blade5."
    ::= { blade5InsCPUSocketEntry 3 }

blade5InsCPUSocketCPUName    OBJECT-TYPE
    SYNTAX    DisplayString (SIZE(0..40))
    MAX-ACCESS    read-only
    STATUS    current
    DESCRIPTION    "This shows the CPU name of CPU socket of server blade5."
    ::= { blade5InsCPUSocketEntry 4 }

blade5InsCPUSocketCPUFrequency    OBJECT-TYPE
    SYNTAX    Integer32
    UNITS    "MHz"
    MAX-ACCESS    read-only
    STATUS    current
    DESCRIPTION    "This shows the CPU frequency of CPU socket of server blade5."
    ::= { blade5InsCPUSocketEntry 5 }

blade5InsCPUSocketCPUStepping    OBJECT-TYPE
    SYNTAX    DisplayString 
    MAX-ACCESS    read-only
    STATUS    current
    DESCRIPTION    "This shows the CPU stepping of CPU socket of server blade5."
    ::= { blade5InsCPUSocketEntry 6 }

blade5InsCPUSocketCPUCoreNum    OBJECT-TYPE
    SYNTAX    Integer32
    MAX-ACCESS    read-only
    STATUS    current
    DESCRIPTION    "This shows the CPU core number of CPU socket of server blade5."
    ::= { blade5InsCPUSocketEntry 7 }

blade5InsCPUSocketCPUUpperLimitTemp    OBJECT-TYPE
    SYNTAX    Integer32
    UNITS    "0.1 degrees C"
    MAX-ACCESS    read-only
    STATUS    current
    DESCRIPTION    "This shows the maximum limited CPU temperature of server blade5."
    ::= { blade5InsCPUSocketEntry 8 }

blade5InsCPUSocketCPULowerLimitTemp    OBJECT-TYPE
    SYNTAX    Integer32
    UNITS    "0.1 degrees C"
    MAX-ACCESS    read-only
    STATUS    current
    DESCRIPTION    "This shows the minimum limited CPU temperature of server blade5."
    ::= { blade5InsCPUSocketEntry 9 }

blade5InsDIMMCapacity    OBJECT-TYPE
    SYNTAX    Integer32
    UNITS    "GB"
    MAX-ACCESS    read-only
    STATUS    current
    DESCRIPTION    "This shows the total amount of DIMM capacity of server blade5."
    ::= { blade5Install 2 }

Blade5InsCPUSocketEntry ::= SEQUENCE {
    blade5InsCPUSocketIndex
        Integer32,
    blade5InsCPUSocketNum
        Integer32,
    blade5InsCPUSocketExist
        INTEGER,
    blade5InsCPUSocketCPUName
        DisplayString,
    blade5InsCPUSocketCPUFrequency
        Integer32,
    blade5InsCPUSocketCPUStepping
        DisplayString,
    blade5InsCPUSocketCPUCoreNum
        Integer32,
    blade5InsCPUSocketCPUUpperLimitTemp
        Integer32,
    blade5InsCPUSocketCPULowerLimitTemp
        Integer32,
    blade5InsDIMMCapacity
        Integer32
}

blade5InsDIMMSlotTable    OBJECT-TYPE
    SYNTAX SEQUENCE OF blade5InsDIMMSlotEntry
    MAX-ACCESS not-accessible
    STATUS     current
    DESCRIPTION "This shows the table of DIMM slot of server blade5."
    ::= { blade5Install 3 }

blade5InsDIMMSlotEntry    OBJECT-TYPE
    SYNTAX Blade5InsDIMMSlotEntry
    MAX-ACCESS not-accessible
    STATUS    current
    DESCRIPTION "This shows the entry of DIMM slot of server blade5."
    INDEX { blade5InsDIMMSlotIndex }
    ::= { blade5InsDIMMSlotTable 1 }

blade5InsDIMMSlotIndex    OBJECT-TYPE
    SYNTAX    Integer32
    MAX-ACCESS    read-only
    STATUS    current
    DESCRIPTION    "This shows the index of DIMM slot of server blade5."
    ::= { blade5InsDIMMSlotEntry 1 }

blade5InsDIMMSlotExist    OBJECT-TYPE
    SYNTAX    INTEGER {
    non-exist(1), exist(2), unknown(3)
    }
    MAX-ACCESS    read-only
    STATUS    current
    DESCRIPTION    "This shows the registrated state of DIMM slot of server blade5."
    ::= { blade5InsDIMMSlotEntry 2 }

blade5InsDIMMSlotDIMMCapacity    OBJECT-TYPE
    SYNTAX    Integer32
    UNITS    "GB"
    MAX-ACCESS    read-only
    STATUS    current
    DESCRIPTION    "This shows the capacity of DIMM slots of server blade5."
    ::= { blade5InsDIMMSlotEntry 3 }

blade5InsDIMMSlotDIMMType    OBJECT-TYPE
    SYNTAX    DisplayString 
    MAX-ACCESS    read-only
    STATUS    current
    DESCRIPTION    "This shows the DIMM type of DIMM slot of server blade5."
    ::= { blade5InsDIMMSlotEntry 4 }

blade5InsDIMMSlotDIMMFrequency    OBJECT-TYPE
    SYNTAX    Integer32
    UNITS    "MHz"
    MAX-ACCESS    read-only
    STATUS    current
    DESCRIPTION    "This shows the DIMM frequency of DIMM slot of server blade5."
    ::= { blade5InsDIMMSlotEntry 5 }

blade5InsDIMMSlotDIMMCasLatency    OBJECT-TYPE
    SYNTAX    Integer32
    MAX-ACCESS    read-only
    STATUS    current
    DESCRIPTION    "This shows the DIMM cas latency of DIMM slot of server blade5."
    ::= { blade5InsDIMMSlotEntry 6 }

blade5InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade5."
    ::= { blade5InsDIMMSlotEntry 7 }

Blade5InsDIMMSlotEntry ::= SEQUENCE {
    blade5InsDIMMSlotIndex
        Integer32,
    blade5InsDIMMSlotExist
        INTEGER,
    blade5InsDIMMSlotDIMMCapacity
        Integer32,
    blade5InsDIMMSlotDIMMType
        DisplayString,
    blade5InsDIMMSlotDIMMFrequency
        Integer32,
    blade5InsDIMMSlotDIMMCasLatency
        Integer32,
    blade5InsDIMMSlotDIMMStatus
        INTEGER
}

blade5InsPCISlotTable    OBJECT-TYPE
    SYNTAX SEQUENCE OF blade5InsPCISlotEntry
    MAX-ACCESS not-accessible
    STATUS     current
    DESCRIPTION "This shows the table of PCI slot of server blade5."
    ::= { blade5Install 4 }

blade5InsPCISlotEntry    OBJECT-TYPE
    SYNTAX Blade5InsPCISlotEntry
    MAX-ACCESS not-accessible
    STATUS    current
    DESCRIPTION "This shows the entry of PCI slot of server blade5."
    INDEX { blade5InsPCISlotIndex }
    ::= { blade5InsPCISlotTable 1 }

blade5InsPCISlotIndex    OBJECT-TYPE
    SYNTAX    Integer32
    MAX-ACCESS    read-only
    STATUS    current
    DESCRIPTION    "This shows the index of PCI slot of server blade5."
    ::= { blade5InsPCISlotEntry 1 }

blade5InsPCISlotType    OBJECT-TYPE
    SYNTAX    DisplayString 
    MAX-ACCESS    read-only
    STATUS    current
    DESCRIPTION    "This shows the type of PCI slot of server blade5."
    ::= { blade5InsPCISlotEntry 2 }

blade5InsPCISlotExist    OBJECT-TYPE
    SYNTAX    INTEGER {
    non-exist(1), exist(2), unknown(3)
    }
    MAX-ACCESS    read-only
    STATUS    current
    DESCRIPTION    "This shows the registrated state of PCI slot of server blade5."
    ::= { blade5InsPCISlotEntry 3 }

blade5InsPCISlotPCIType    OBJECT-TYPE
    SYNTAX    DisplayString 
    MAX-ACCESS    read-only
    STATUS    current
    DESCRIPTION    "This shows the PCI type of PCI slot of server blade5."
    ::= { blade5InsPCISlotEntry 4 }

blade5InsPCISlotPCIProductName    OBJECT-TYPE
    SYNTAX    DisplayString 
    MAX-ACCESS    read-only
    STATUS    current
    DESCRIPTION    "This shows the PCI product name of PCI slot of server blade5."
    ::= { blade5InsPCISlotEntry 5 }

blade5InsPCISlotPCISerial    OBJECT-TYPE
    SYNTAX    DisplayString 
    MAX-ACCESS    read-only
    STATUS    current
    DESCRIPTION    "This shows the serial number of PCI slot of server blade5."
    ::= { blade5InsPCISlotEntry 6 }

blade5InsPCISlotPCIManufacturer    OBJECT-TYPE
    SYNTAX    DisplayString 
    MAX-ACCESS    read-only
    STATUS    current
    DESCRIPTION    "This shows the manufacturer of PCI slot of server blade5."
    ::= { blade5InsPCISlotEntry 7 }

blade5InsPCISlotNum    OBJECT-TYPE
    SYNTAX    Integer32
    MAX-ACCESS    read-only
    STATUS    current
    DESCRIPTION    "This shows the number of PCI slots of server blade5."
    ::= { blade5InsPCISlotEntry 8 }

Blade5InsPCISlotEntry ::= SEQUENCE {
    blade5InsPCISlotIndex
        Integer32,
    blade5InsPCISlotType
        DisplayString,
    blade5InsPCISlotExist
        INTEGER,
    blade5InsPCISlotPCIType
        DisplayString,
    blade5InsPCISlotPCIProductName
        DisplayString,
    blade5InsPCISlotPCISerial
        DisplayString,
    blade5InsPCISlotPCIManufacturer
        DisplayString,
    blade5InsPCISlotNum
        Integer32
}

blade5InsLOMTable    OBJECT-TYPE
    SYNTAX SEQUENCE OF blade5InsLOMEntry
    MAX-ACCESS not-accessible
    STATUS     current
    DESCRIPTION "This shows the table of onboard LAN of server blade5."
    ::= { blade5Install 5 }

blade5InsLOMEntry    OBJECT-TYPE
    SYNTAX Blade5InsLOMEntry
    MAX-ACCESS not-accessible
    STATUS    current
    DESCRIPTION "This shows the entry of onboard LAN of server blade5."
    INDEX { blade5InsLOMIndex }
    ::= { blade5InsLOMTable 1 }

blade5InsLOMIndex    OBJECT-TYPE
    SYNTAX    Integer32
    MAX-ACCESS    read-only
    STATUS    current
    DESCRIPTION    "This shows the index of onboard LAN of server blade5."
    ::= { blade5InsLOMEntry 1 }

blade5InsLOMType    OBJECT-TYPE
    SYNTAX    DisplayString 
    MAX-ACCESS    read-only
    STATUS    current
    DESCRIPTION    "This shows the type of onboard LAN of server blade5."
    ::= { blade5InsLOMEntry 2 }

blade5InsLOMLinkSpeed    OBJECT-TYPE
    SYNTAX    Integer32
    UNITS    "bps"
    MAX-ACCESS    read-only
    STATUS    current
    DESCRIPTION    "This shows the link speed of onboard LAN of server blade5."
    ::= { blade5InsLOMEntry 3 }

blade5InsLOMMAC    OBJECT-TYPE
    SYNTAX    DisplayString 
    MAX-ACCESS    read-only
    STATUS    current
    DESCRIPTION    "This shows the MAC address of onboard LAN of server blade5."
    ::= { blade5InsLOMEntry 4 }

blade5InsLOMLinkStatus    OBJECT-TYPE
    SYNTAX    INTEGER {
    up (1),down (2),unknown (3)
    }
    MAX-ACCESS    read-only
    STATUS    current
    DESCRIPTION    "This shows the link state of onboard LAN of server blade5."
    ::= { blade5InsLOMEntry 5 }

blade5InsLOMPortDivide    OBJECT-TYPE
    SYNTAX    INTEGER {
    possible (1),Impossible (2),unknown (3)
    }
    MAX-ACCESS    read-only
    STATUS    current
    DESCRIPTION    "This shows the port divide propriety of onboard LAN of server blade5."
    ::= { blade5InsLOMEntry 6 }

blade5InsLOMPortDivideNum    OBJECT-TYPE
    SYNTAX    Integer32
    MAX-ACCESS    read-only
    STATUS    current
    DESCRIPTION    "This shows the port divide number of onboard LAN of server blade5."
    ::= { blade5InsLOMEntry 7 }

Blade5InsLOMEntry ::= SEQUENCE {
    blade5InsLOMIndex
        Integer32,
    blade5InsLOMType
        DisplayString,
    blade5InsLOMLinkSpeed
        Integer32,
    blade5InsLOMMAC
        DisplayString,
    blade5InsLOMLinkStatus
        INTEGER,
    blade5InsLOMPortDivide
        INTEGER,
    blade5InsLOMPortDivideNum
        Integer32
}

blade5HDDSlotTable    OBJECT-TYPE
    SYNTAX SEQUENCE OF blade5HDDSlotEntry
    MAX-ACCESS not-accessible
    STATUS     current
    DESCRIPTION "This shows the table of HDD slot of server blade5."
    ::= { blade5Install 7 }

blade5HDDSlotEntry    OBJECT-TYPE
    SYNTAX Blade5HDDSlotEntry
    MAX-ACCESS not-accessible
    STATUS    current
    DESCRIPTION "This shows the entry of HDD slot of server blade5."
    INDEX { blade5HDDSlotIndex }
    ::= { blade5HDDSlotTable 1 }

blade5HDDSlotIndex    OBJECT-TYPE
    SYNTAX    Integer32
    MAX-ACCESS    read-only
    STATUS    current
    DESCRIPTION    "This shows the index of HDD slot of server blade5."
    ::= { blade5HDDSlotEntry 1 }

blade5HDDSlotNum    OBJECT-TYPE
    SYNTAX    Integer32
    MAX-ACCESS    read-only
    STATUS    current
    DESCRIPTION    "This shows the number of HDD slots of server blade5."
    ::= { blade5HDDSlotEntry 2 }

blade5HDDSlotExist    OBJECT-TYPE
    SYNTAX    INTEGER {
    non-exist(1), exist(2), unknown(3)
    }
    MAX-ACCESS    read-only
    STATUS    current
    DESCRIPTION    "This shows the registrated state of HDD slot of server blade5."
    ::= { blade5HDDSlotEntry 3 }

blade5HDDSlotHDDType    OBJECT-TYPE
    SYNTAX    DisplayString 
    MAX-ACCESS    read-only
    STATUS    current
    DESCRIPTION    "This shows the HDD type of HDD slot of server blade5."
    ::= { blade5HDDSlotEntry 4 }

blade5HDDSlotHDDProductName    OBJECT-TYPE
    SYNTAX    DisplayString 
    MAX-ACCESS    read-only
    STATUS    current
    DESCRIPTION    "This shows the HDD product name of HDD slot of server blade5."
    ::= { blade5HDDSlotEntry 5 }

blade5HDDSlotHDDModel    OBJECT-TYPE
    SYNTAX    DisplayString 
    MAX-ACCESS    read-only
    STATUS    current
    DESCRIPTION    "This shows the HDD model of HDD slot of server blade5."
    ::= { blade5HDDSlotEntry 6 }

blade5HDDSlotHDDSerialNum    OBJECT-TYPE
    SYNTAX    DisplayString 
    MAX-ACCESS    read-only
    STATUS    current
    DESCRIPTION    "This shows the HDD serial number of HDD slot of server blade5."
    ::= { blade5HDDSlotEntry 7 }

blade5HDDSlotHDDCapacity    OBJECT-TYPE
    SYNTAX    Integer32
    UNITS    "GB"
    MAX-ACCESS    read-only
    STATUS    current
    DESCRIPTION    "This shows the HDD capacity of HDD slots of server blade5."
    ::= { blade5HDDSlotEntry 8 }

blade5HDDSlotHDDRPM    OBJECT-TYPE
    SYNTAX    Integer32
    UNITS    "rpm"
    MAX-ACCESS    read-only
    STATUS    current
    DESCRIPTION    "This shows the HDD drive speed of HDD slot of server blade5."
    ::= { blade5HDDSlotEntry 9 }

blade5HDDSlotHDDStatePower    OBJECT-TYPE
    SYNTAX    INTEGER {
    poweroff (1), poweron (2), unknown (3)
    }
    MAX-ACCESS    read-only
    STATUS    current
    DESCRIPTION    "This shows the HDD power supply state of HDD slot of server blade5."
    ::= { blade5HDDSlotEntry 10 }

blade5HDDSlotHDDStateHealth    OBJECT-TYPE
    SYNTAX    INTEGER {
    normal (1),fail (2),unknown (3),rebuild (4)
    }
    MAX-ACCESS    read-only
    STATUS    current
    DESCRIPTION    "This shows the HDD health state of HDD slot of server blade5."
    ::= { blade5HDDSlotEntry 11 }

blade5HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade5(activity)."
    ::= { blade5HDDSlotEntry 12 }

blade5HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade5(status)."
    ::= { blade5HDDSlotEntry 13 }

blade5HDDSlotHDDFWInfoName    OBJECT-TYPE
    SYNTAX    DisplayString 
    MAX-ACCESS    read-only
    STATUS    current
    DESCRIPTION    "This shows the HDD firmware name of HDD slot of server blade5."
    ::= { blade5HDDSlotEntry 20 }

blade5HDDSlotHDDFWInfoCurrentVer    OBJECT-TYPE
    SYNTAX    DisplayString 
    MAX-ACCESS    read-only
    STATUS    current
    DESCRIPTION    "This shows the HDD firmware current version of HDD slot of server blade5."
    ::= { blade5HDDSlotEntry 21 }

blade5HDDSlotHDDFWInfoNextVer    OBJECT-TYPE
    SYNTAX    DisplayString 
    MAX-ACCESS    read-only
    STATUS    current
    DESCRIPTION    "This shows the HDD firmware next version of HDD slot of server blade5."
    ::= { blade5HDDSlotEntry 22 }

Blade5HDDSlotEntry ::= SEQUENCE {
    blade5HDDSlotIndex
        Integer32,
    blade5HDDSlotNum
        Integer32,
    blade5HDDSlotExist
        INTEGER,
    blade5HDDSlotHDDType
        DisplayString,
    blade5HDDSlotHDDProductName
        DisplayString,
    blade5HDDSlotHDDModel
        DisplayString,
    blade5HDDSlotHDDSerialNum
        DisplayString,
    blade5HDDSlotHDDCapacity
        Integer32,
    blade5HDDSlotHDDRPM
        Integer32,
    blade5HDDSlotHDDStatePower
        INTEGER,
    blade5HDDSlotHDDStateHealth
        INTEGER,
    blade5HDDSlotHDDStateLEDACT
        INTEGER,
    blade5HDDSlotHDDStateLEDSTS
        INTEGER,
    blade5HDDSlotHDDFWInfoName
        DisplayString,
    blade5HDDSlotHDDFWInfoCurrentVer
        DisplayString,
    blade5HDDSlotHDDFWInfoNextVer
        DisplayString
}

blade5ExpansionHDDSlotTable    OBJECT-TYPE
    SYNTAX SEQUENCE OF blade5ExpansionHDDSlotEntry
    MAX-ACCESS not-accessible
    STATUS     current
    DESCRIPTION "This shows the table of expansion HDD slot of server blade5."
    ::= { blade5Install 8 }

blade5ExpansionHDDSlotEntry    OBJECT-TYPE
    SYNTAX Blade5ExpansionHDDSlotEntry
    MAX-ACCESS not-accessible
    STATUS    current
    DESCRIPTION "This shows the entry of expansion HDD slot of server blade5."
    INDEX { blade5ExpansionHDDSlotIndex }
    ::= { blade5ExpansionHDDSlotTable 1 }

blade5ExpansionHDDSlotIndex    OBJECT-TYPE
    SYNTAX    Integer32
    MAX-ACCESS    read-only
    STATUS    current
    DESCRIPTION    "This shows the index of expansion HDD slot of server blade5."
    ::= { blade5ExpansionHDDSlotEntry 1 }

blade5ExpansionHDDSlotNum    OBJECT-TYPE
    SYNTAX    Integer32
    MAX-ACCESS    read-only
    STATUS    current
    DESCRIPTION    "This shows the number of expansion HDD slots of server blade5."
    ::= { blade5ExpansionHDDSlotEntry 2 }

blade5ExpansionHDDSlotExist    OBJECT-TYPE
    SYNTAX    INTEGER {
    non-exist(1), exist(2), unknown(3)
    }
    MAX-ACCESS    read-only
    STATUS    current
    DESCRIPTION    "This shows the registrated state of expansion HDD slot of server blade5."
    ::= { blade5ExpansionHDDSlotEntry 3 }

blade5ExpansionHDDSlotHDDType    OBJECT-TYPE
    SYNTAX    DisplayString 
    MAX-ACCESS    read-only
    STATUS    current
    DESCRIPTION    "This shows the HDD type of expansion HDD slot of server blade5."
    ::= { blade5ExpansionHDDSlotEntry 4 }

blade5ExpansionHDDSlotHDDProductName    OBJECT-TYPE
    SYNTAX    DisplayString 
    MAX-ACCESS    read-only
    STATUS    current
    DESCRIPTION    "This shows the HDD product name of expansion HDD slot of server blade5."
    ::= { blade5ExpansionHDDSlotEntry 5 }

blade5ExpansionHDDSlotHDDModel    OBJECT-TYPE
    SYNTAX    DisplayString 
    MAX-ACCESS    read-only
    STATUS    current
    DESCRIPTION    "This shows the HDD model of expansion HDD slot of server blade5."
    ::= { blade5ExpansionHDDSlotEntry 6 }

blade5ExpansionHDDSlotHDDSerialNum    OBJECT-TYPE
    SYNTAX    DisplayString 
    MAX-ACCESS    read-only
    STATUS    current
    DESCRIPTION    "This shows the HDD serial number of expansion HDD slot of server blade5."
    ::= { blade5ExpansionHDDSlotEntry 7 }

blade5ExpansionHDDSlotHDDCapacity    OBJECT-TYPE
    SYNTAX    Integer32
    UNITS    "GB"
    MAX-ACCESS    read-only
    STATUS    current
    DESCRIPTION    "This shows the HDD capacity of expansion HDD slots of server blade5."
    ::= { blade5ExpansionHDDSlotEntry 8 }

blade5ExpansionHDDSlotHDDRPM    OBJECT-TYPE
    SYNTAX    Integer32
    UNITS    "rpm"
    MAX-ACCESS    read-only
    STATUS    current
    DESCRIPTION    "This shows the HDD drive speed of expansion HDD slot of server blade5."
    ::= { blade5ExpansionHDDSlotEntry 9 }

blade5ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade5."
    ::= { blade5ExpansionHDDSlotEntry 10 }

blade5ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade5."
    ::= { blade5ExpansionHDDSlotEntry 11 }

blade5ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade5(activity)."
    ::= { blade5ExpansionHDDSlotEntry 12 }

blade5ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade5(status)."
    ::= { blade5ExpansionHDDSlotEntry 13 }

blade5ExpansionHDDSlotHDDFWInfoName    OBJECT-TYPE
    SYNTAX    DisplayString 
    MAX-ACCESS    read-only
    STATUS    current
    DESCRIPTION    "This shows the HDD firmware name of expansion HDD slot of server blade5."
    ::= { blade5ExpansionHDDSlotEntry 20 }

blade5ExpansionHDDSlotHDDFWInfoCurrentVer    OBJECT-TYPE
    SYNTAX    DisplayString 
    MAX-ACCESS    read-only
    STATUS    current
    DESCRIPTION    "This shows the HDD firmware current version of expansion HDD slot of server blade5."
    ::= { blade5ExpansionHDDSlotEntry 21 }

blade5ExpansionHDDSlotHDDFWInfoNextVer    OBJECT-TYPE
    SYNTAX    DisplayString 
    MAX-ACCESS    read-only
    STATUS    current
    DESCRIPTION    "This shows the HDD firmware next version of expansion HDD slot of server blade5."
    ::= { blade5ExpansionHDDSlotEntry 22 }

Blade5ExpansionHDDSlotEntry ::= SEQUENCE {
    blade5ExpansionHDDSlotIndex
        Integer32,
    blade5ExpansionHDDSlotNum
        Integer32,
    blade5ExpansionHDDSlotExist
        INTEGER,
    blade5ExpansionHDDSlotHDDType
        DisplayString,
    blade5ExpansionHDDSlotHDDProductName
        DisplayString,
    blade5ExpansionHDDSlotHDDModel
        DisplayString,
    blade5ExpansionHDDSlotHDDSerialNum
        DisplayString,
    blade5ExpansionHDDSlotHDDCapacity
        Integer32,
    blade5ExpansionHDDSlotHDDRPM
        Integer32,
    blade5ExpansionHDDSlotHDDStatePower
        INTEGER,
    blade5ExpansionHDDSlotHDDStateHealth
        INTEGER,
    blade5ExpansionHDDSlotHDDStateLEDACT
        INTEGER,
    blade5ExpansionHDDSlotHDDStateLEDSTS
        INTEGER,
    blade5ExpansionHDDSlotHDDFWInfoName
        DisplayString,
    blade5ExpansionHDDSlotHDDFWInfoCurrentVer
        DisplayString,
    blade5ExpansionHDDSlotHDDFWInfoNextVer
        DisplayString
}

blade5VoltageSensorTable    OBJECT-TYPE
    SYNTAX SEQUENCE OF blade5VoltageSensorEntry
    MAX-ACCESS not-accessible
    STATUS     current
    DESCRIPTION "This shows the table of voltage sensor of server blade5."
    ::= { blade5State 40 }

blade5VoltageSensorEntry    OBJECT-TYPE
    SYNTAX Blade5VoltageSensorEntry
    MAX-ACCESS not-accessible
    STATUS    current
    DESCRIPTION "This shows the entry of voltage sensor of server blade5."
    INDEX { blade5VoltageSensorIndex }
    ::= { blade5VoltageSensorTable 1 }

blade5VoltageSensorIndex    OBJECT-TYPE
    SYNTAX    Integer32
    MAX-ACCESS    read-only
    STATUS    current
    DESCRIPTION    "This shows the index of voltage sensor of server blade5."
    ::= { blade5VoltageSensorEntry 1 }

blade5VoltageSensorName    OBJECT-TYPE
    SYNTAX    DisplayString 
    MAX-ACCESS    read-only
    STATUS    current
    DESCRIPTION    "This shows the voltage sensor name of server blade5."
    ::= { blade5VoltageSensorEntry 2 }

blade5VoltageSensorValue    OBJECT-TYPE
    SYNTAX    Integer32
    UNITS    "0.1 V"
    MAX-ACCESS    read-only
    STATUS    current
    DESCRIPTION    "This shows the voltage sensor value of server blade5."
    ::= { blade5VoltageSensorEntry 3 }

blade5VoltageSensorValid    OBJECT-TYPE
    SYNTAX    INTEGER {
    invalid (1),valid (2),unknown (3)
    }
    MAX-ACCESS    read-only
    STATUS    current
    DESCRIPTION    "This shows the validity of voltage sensor value of server blade5."
    ::= { blade5VoltageSensorEntry 4 }

Blade5VoltageSensorEntry ::= SEQUENCE {
    blade5VoltageSensorIndex
        Integer32,
    blade5VoltageSensorName
        DisplayString,
    blade5VoltageSensorValue
        Integer32,
    blade5VoltageSensorValid
        INTEGER
}

blade5TempSensorTable    OBJECT-TYPE
    SYNTAX SEQUENCE OF blade5TempSensorEntry
    MAX-ACCESS not-accessible
    STATUS     current
    DESCRIPTION "This shows the table of temperature sensor of server blade5."
    ::= { blade5State 41 }

blade5TempSensorEntry    OBJECT-TYPE
    SYNTAX Blade5TempSensorEntry
    MAX-ACCESS not-accessible
    STATUS    current
    DESCRIPTION "This shows the entry of temperature sensor of server blade5."
    INDEX { blade5TempSensorIndex }
    ::= { blade5TempSensorTable 1 }

blade5TempSensorIndex    OBJECT-TYPE
    SYNTAX    Integer32
    MAX-ACCESS    read-only
    STATUS    current
    DESCRIPTION    "This shows the index of temperature sensor of server blade5."
    ::= { blade5TempSensorEntry 1 }

blade5TempSensorName    OBJECT-TYPE
    SYNTAX    DisplayString 
    MAX-ACCESS    read-only
    STATUS    current
    DESCRIPTION    "This shows the temperature sensor name of server blade5."
    ::= { blade5TempSensorEntry 2 }

blade5TempSensorValue    OBJECT-TYPE
    SYNTAX    Integer32
    UNITS    "0.1 degrees C"
    MAX-ACCESS    read-only
    STATUS    current
    DESCRIPTION    "This shows the temperature sensor value of server blade5."
    ::= { blade5TempSensorEntry 3 }

blade5TempSensorValid    OBJECT-TYPE
    SYNTAX    INTEGER {
    invalid (1),valid (2),unknown (3)
    }
    MAX-ACCESS    read-only
    STATUS    current
    DESCRIPTION    "This shows the validity of temperature sensor value of server blade5."
    ::= { blade5TempSensorEntry 4 }

Blade5TempSensorEntry ::= SEQUENCE {
    blade5TempSensorIndex
        Integer32,
    blade5TempSensorName
        DisplayString,
    blade5TempSensorValue
        Integer32,
    blade5TempSensorValid
        INTEGER
}

blade5FWInfo    OBJECT IDENTIFIER ::= { blade5 5 } 

blade5FWInfoTotalCurrentVer    OBJECT-TYPE
    SYNTAX    DisplayString (SIZE(0..40))
    MAX-ACCESS    read-only
    STATUS    current
    DESCRIPTION    "This shows the total current version of firmware of server blade5."
    ::= { blade5FWInfo 1 }

blade5FWInfoTotalNextVer    OBJECT-TYPE
    SYNTAX    DisplayString (SIZE(0..40))
    MAX-ACCESS    read-only
    STATUS    current
    DESCRIPTION    "This shows the total next version of firmware of server blade5."
    ::= { blade5FWInfo 2 }

blade5FWInfoTable    OBJECT-TYPE
    SYNTAX SEQUENCE OF blade5FWInfoEntry
    MAX-ACCESS not-accessible
    STATUS     current
    DESCRIPTION "This shows the table of firmware information of server blade5."
    ::= { blade5FWInfo 3 }

blade5FWInfoEntry    OBJECT-TYPE
    SYNTAX Blade5FWInfoEntry
    MAX-ACCESS not-accessible
    STATUS    current
    DESCRIPTION "This shows the entry of firmware information of server blade5."
    INDEX { blade5FWInfoIndex }
    ::= { blade5FWInfoTable 1 }

blade5FWInfoIndex    OBJECT-TYPE
    SYNTAX    Integer32
    MAX-ACCESS    read-only
    STATUS    current
    DESCRIPTION    "This shows the index of firmware information of server blade5."
    ::= { blade5FWInfoEntry 1 }

blade5FWInfoName    OBJECT-TYPE
    SYNTAX    DisplayString (SIZE(0..40))
    MAX-ACCESS    read-only
    STATUS    current
    DESCRIPTION    "This shows the firmware name of server blade5."
    ::= { blade5FWInfoEntry 2 }

blade5FWCurrentVer    OBJECT-TYPE
    SYNTAX    DisplayString (SIZE(0..40))
    MAX-ACCESS    read-only
    STATUS    current
    DESCRIPTION    "This shows the firmware current version of server blade5."
    ::= { blade5FWInfoEntry 3 }

blade5FWInfoNextVer    OBJECT-TYPE
    SYNTAX    DisplayString (SIZE(0..40))
    MAX-ACCESS    read-only
    STATUS    current
    DESCRIPTION    "This shows the firmware next version of server blade5."
    ::= { blade5FWInfoEntry 4 }

blade5FWInfoHVMCurrentVer    OBJECT-TYPE
    SYNTAX    DisplayString (SIZE(0..40))
    MAX-ACCESS    read-only
    STATUS    current
    DESCRIPTION    "This shows the HVM current version of server blade5."
    ::= { blade5FWInfo 4 }

blade5FWInfoHVMNextVer    OBJECT-TYPE
    SYNTAX    DisplayString (SIZE(0..40))
    MAX-ACCESS    read-only
    STATUS    current
    DESCRIPTION    "This shows the HVM next version of server blade5."
    ::= { blade5FWInfo 5 }

Blade5FWInfoEntry ::= SEQUENCE {
    blade5FWInfoIndex
        Integer32,
    blade5FWInfoName
        DisplayString,
    blade5FWCurrentVer
        DisplayString,
    blade5FWInfoNextVer
        DisplayString,
    blade5FWInfoHVMCurrentVer
        DisplayString,
    blade5FWInfoHVMNextVer
        DisplayString
}

blade6    OBJECT IDENTIFIER ::= { blade 6 } 

blade6BasicInfo    OBJECT IDENTIFIER ::= { blade6 1 } 

blade6InfoProductName    OBJECT-TYPE
    SYNTAX    DisplayString (SIZE(0..40))
    MAX-ACCESS    read-only
    STATUS    current
    DESCRIPTION    "This shows the product name of server blade6."
    ::= { blade6BasicInfo 1 }

blade6InfoModel    OBJECT-TYPE
    SYNTAX    DisplayString (SIZE(0..40))
    MAX-ACCESS    read-only
    STATUS    current
    DESCRIPTION    "This shows the model name of server blade6."
    ::= { blade6BasicInfo 2 }

blade6InfoSerialNum    OBJECT-TYPE
    SYNTAX    DisplayString (SIZE(0..40))
    MAX-ACCESS    read-only
    STATUS    current
    DESCRIPTION    "This shows the serial number of server blade6."
    ::= { blade6BasicInfo 3 }

blade6InfoProductVersion    OBJECT-TYPE
    SYNTAX    DisplayString (SIZE(0..40))
    MAX-ACCESS    read-only
    STATUS    current
    DESCRIPTION    "This shows the product version of server blade6."
    ::= { blade6BasicInfo 4 }

blade6InfoProductManufacturer    OBJECT-TYPE
    SYNTAX    DisplayString (SIZE(0..40))
    MAX-ACCESS    read-only
    STATUS    current
    DESCRIPTION    "This shows the product manufacturer of server blade6."
    ::= { blade6BasicInfo 5 }

blade6InfoBoardProductName    OBJECT-TYPE
    SYNTAX    DisplayString (SIZE(0..40))
    MAX-ACCESS    read-only
    STATUS    current
    DESCRIPTION    "This shows the board product name of server blade6."
    ::= { blade6BasicInfo 7 }

blade6InfoBoardSerialNum    OBJECT-TYPE
    SYNTAX    DisplayString (SIZE(0..40))
    MAX-ACCESS    read-only
    STATUS    current
    DESCRIPTION    "This shows the board serial number of server blade6."
    ::= { blade6BasicInfo 8 }

blade6InfoBoardManufacturer    OBJECT-TYPE
    SYNTAX    DisplayString (SIZE(0..40))
    MAX-ACCESS    read-only
    STATUS    current
    DESCRIPTION    "This shows the board manufacturer of server blade6."
    ::= { blade6BasicInfo 9 }

blade6InfoUUID    OBJECT-TYPE
    SYNTAX    DisplayString (SIZE(0..40))
    MAX-ACCESS    read-only
    STATUS    current
    DESCRIPTION    "This shows UUID(universal Unique ID) of server blade6."
    ::= { blade6BasicInfo 10 }

blade6InfoLogicalPartitionSupport    OBJECT-TYPE
    SYNTAX    INTEGER {
    not-support(1), support(2),unknown(3)
    }
    MAX-ACCESS    read-only
    STATUS    current
    DESCRIPTION    "This shows whether the server blade6 supports HVM or not of server blade1."
    ::= { blade6BasicInfo 11 }

blade6InfoRemoteKVMSupport    OBJECT-TYPE
    SYNTAX    INTEGER {
    not-support(1), support(2),unknown(3)
    }
    MAX-ACCESS    read-only
    STATUS    current
    DESCRIPTION    "This shows whether the server blade6 supports remote KVM or not of server blade1."
    ::= { blade6BasicInfo 12 }

blade6InfoSpec    OBJECT IDENTIFIER ::= { blade6BasicInfo 20 } 

blade6SpecInputCurrentType    OBJECT-TYPE
    SYNTAX    INTEGER {
    ac(1),dc(2),unknown(3)
    }
    MAX-ACCESS    read-only
    STATUS    current
    DESCRIPTION    "This shows the currency type of server blade6."
    ::= { blade6InfoSpec 1 }

blade6SpecRateVoltage    OBJECT-TYPE
    SYNTAX    Integer32
    UNITS    "0.1 V"
    MAX-ACCESS    read-only
    STATUS    current
    DESCRIPTION    "This shows the rated voltage of server blade6."
    ::= { blade6InfoSpec 2 }

blade6SpecConsumptionCurrent    OBJECT-TYPE
    SYNTAX    Integer32
    UNITS    "0.1 A"
    MAX-ACCESS    read-only
    STATUS    current
    DESCRIPTION    "This shows the consumption current of server blade6."
    ::= { blade6InfoSpec 3 }

blade6SpecPowerConsumption    OBJECT-TYPE
    SYNTAX    Integer32
    UNITS    "W"
    MAX-ACCESS    read-only
    STATUS    current
    DESCRIPTION    "This shows the power consumption of server blade6."
    ::= { blade6InfoSpec 4 }

blade6SpecMass    OBJECT-TYPE
    SYNTAX    Integer32
    UNITS    "0.1 kg"
    MAX-ACCESS    read-only
    STATUS    current
    DESCRIPTION    "This shows the weight of server blade6."
    ::= { blade6InfoSpec 5 }

blade6InfoUpperLimitIntakeTemp    OBJECT-TYPE
    SYNTAX    Integer32
    UNITS    "0.1 degrees C"
    MAX-ACCESS    read-only
    STATUS    current
    DESCRIPTION    "This shows the maximum limited intake temperature of server blade6."
    ::= { blade6InfoSpec 6 }

blade6InfoLowerLimitIntakeTemp    OBJECT-TYPE
    SYNTAX    Integer32
    UNITS    "0.1 degrees C"
    MAX-ACCESS    read-only
    STATUS    current
    DESCRIPTION    "This shows the minimum limited intake temperature of server blade6."
    ::= { blade6InfoSpec 7 }

blade6SpecSize    OBJECT-TYPE
    SYNTAX    DisplayString (SIZE(0..40))
    MAX-ACCESS    read-only
    STATUS    current
    DESCRIPTION    "This shows the size of server blade6."
    ::= { blade6InfoSpec 8 }

blade6SpecOccupySlots    OBJECT-TYPE
    SYNTAX    Integer32
    MAX-ACCESS    read-only
    STATUS    current
    DESCRIPTION    "This shows the dedicated number of slots of server blade6."
    ::= { blade6InfoSpec 9 }

blade6SpecExpansionBladeSlot    OBJECT-TYPE
    SYNTAX    Integer32
    MAX-ACCESS    read-only
    STATUS    current
    DESCRIPTION    "This shows the number of slots of expansion blade of server blade6."
    ::= { blade6InfoSpec 10 }

blade6InfoExpansionBladeTable    OBJECT-TYPE
    SYNTAX SEQUENCE OF blade6InfoExpansionBladeEntry
    MAX-ACCESS not-accessible
    STATUS     current
    DESCRIPTION "This shows the table of expansion blade slot of server blade6."
    ::= { blade6BasicInfo 30 }

blade6InfoExpansionBladeEntry    OBJECT-TYPE
    SYNTAX Blade6InfoExpansionBladeEntry
    MAX-ACCESS not-accessible
    STATUS    current
    DESCRIPTION "This shows the entry of expansion blade slot of server blade6."
    INDEX { blade6InfoExpansionBladeIndex }
    ::= { blade6InfoExpansionBladeTable 1 }

blade6InfoExpansionBladeIndex    OBJECT-TYPE
    SYNTAX    Integer32
    MAX-ACCESS    read-only
    STATUS    current
    DESCRIPTION    "This shows the index of expansion blade slot of server blade6."
    ::= { blade6InfoExpansionBladeEntry 1 }

blade6InfoExpansionBladeExist    OBJECT-TYPE
    SYNTAX    INTEGER {
    non-exist(1), exist(2), unknown(3)
    }
    MAX-ACCESS    read-only
    STATUS    current
    DESCRIPTION    "This shows the registrated state of expansion blade of server blade6."
    ::= { blade6InfoExpansionBladeEntry 2 }

blade6InfoExpansionBladeProductName    OBJECT-TYPE
    SYNTAX    DisplayString (SIZE(0..40))
    MAX-ACCESS    read-only
    STATUS    current
    DESCRIPTION    "This shows the product name of expansion blade of server blade6."
    ::= { blade6InfoExpansionBladeEntry 3 }

blade6InfoExpansionBladeModel    OBJECT-TYPE
    SYNTAX    DisplayString (SIZE(0..40))
    MAX-ACCESS    read-only
    STATUS    current
    DESCRIPTION    "This shows the model name of expansion blade of server blade6."
    ::= { blade6InfoExpansionBladeEntry 4 }

blade6InfoExpansionBladeSerialNum    OBJECT-TYPE
    SYNTAX    DisplayString (SIZE(0..40))
    MAX-ACCESS    read-only
    STATUS    current
    DESCRIPTION    "This shows the serial number of expansion blade of server blade6."
    ::= { blade6InfoExpansionBladeEntry 5 }

blade6InfoExpansionBladeProductVersion    OBJECT-TYPE
    SYNTAX    DisplayString (SIZE(0..40))
    MAX-ACCESS    read-only
    STATUS    current
    DESCRIPTION    "This shows the product version of expansion blade of server blade6."
    ::= { blade6InfoExpansionBladeEntry 6 }

blade6InfoExpansionBladeProductManufacturer    OBJECT-TYPE
    SYNTAX    DisplayString (SIZE(0..40))
    MAX-ACCESS    read-only
    STATUS    current
    DESCRIPTION    "This shows the product manufacturer of expansion blade of server blade6."
    ::= { blade6InfoExpansionBladeEntry 7 }

blade6InfoExpansionBladeBoardProductName    OBJECT-TYPE
    SYNTAX    DisplayString (SIZE(0..40))
    MAX-ACCESS    read-only
    STATUS    current
    DESCRIPTION    "This shows the board product name of expansion blade of server blade6."
    ::= { blade6InfoExpansionBladeEntry 9 }

blade6InfoExpansionBladeBoardSerialNum    OBJECT-TYPE
    SYNTAX    DisplayString (SIZE(0..40))
    MAX-ACCESS    read-only
    STATUS    current
    DESCRIPTION    "This shows the board serial number of expansion blade of server blade6."
    ::= { blade6InfoExpansionBladeEntry 10 }

blade6InfoExpansionBladeBoardManufacturer    OBJECT-TYPE
    SYNTAX    DisplayString (SIZE(0..40))
    MAX-ACCESS    read-only
    STATUS    current
    DESCRIPTION    "This shows the board manufacturer of expansion blade of server blade6."
    ::= { blade6InfoExpansionBladeEntry 11 }

Blade6InfoExpansionBladeEntry ::= SEQUENCE {
    blade6InfoExpansionBladeIndex
        Integer32,
    blade6InfoExpansionBladeExist
        INTEGER,
    blade6InfoExpansionBladeProductName
        DisplayString,
    blade6InfoExpansionBladeModel
        DisplayString,
    blade6InfoExpansionBladeSerialNum
        DisplayString,
    blade6InfoExpansionBladeProductVersion
        DisplayString,
    blade6InfoExpansionBladeProductManufacturer
        DisplayString,
    blade6InfoExpansionBladeBoardProductName
        DisplayString,
    blade6InfoExpansionBladeBoardSerialNum
        DisplayString,
    blade6InfoExpansionBladeBoardManufacturer
        DisplayString
}

blade6Capacity    OBJECT IDENTIFIER ::= { blade6 2 } 

blade6CapacityCPUSocket    OBJECT-TYPE
    SYNTAX    Integer32
    MAX-ACCESS    read-only
    STATUS    current
    DESCRIPTION    "This shows the capacity of CPU sockets of server blade6."
    ::= { blade6Capacity 1 }

blade6CapacityDIMMSlot    OBJECT-TYPE
    SYNTAX    Integer32
    MAX-ACCESS    read-only
    STATUS    current
    DESCRIPTION    "This shows the capacity of DIMM slots of server blade6."
    ::= { blade6Capacity 2 }

blade6CapacityPCISlot    OBJECT-TYPE
    SYNTAX    Integer32
    MAX-ACCESS    read-only
    STATUS    current
    DESCRIPTION    "This shows the capacity of PCI slots of server blade6."
    ::= { blade6Capacity 3 }

blade6CapacityLOM    OBJECT-TYPE
    SYNTAX    Integer32
    MAX-ACCESS    read-only
    STATUS    current
    DESCRIPTION    "This shows the capacity of onboard LAN ports of server blade6."
    ::= { blade6Capacity 4 }

blade6CapacityFan    OBJECT-TYPE
    SYNTAX    Integer32
    MAX-ACCESS    read-only
    STATUS    current
    DESCRIPTION    "This shows the capacity of onboard fans of server blade6."
    ::= { blade6Capacity 5 }

blade6CapacityHDDSlot    OBJECT-TYPE
    SYNTAX    Integer32
    MAX-ACCESS    read-only
    STATUS    current
    DESCRIPTION    "This shows the capacity of HDD slots of server blade6."
    ::= { blade6Capacity 6 }

blade6CapacityVoltageSensor    OBJECT-TYPE
    SYNTAX    Integer32
    MAX-ACCESS    read-only
    STATUS    current
    DESCRIPTION    "This shows the capacity of voltage sensors of blade6."
    ::= { blade6Capacity 7 }

blade6CapacityTempSensor    OBJECT-TYPE
    SYNTAX    Integer32
    MAX-ACCESS    read-only
    STATUS    current
    DESCRIPTION    "This shows the capacity of temperature sensors of blade6."
    ::= { blade6Capacity 8 }

blade6CapacityExpansionHDDSlot    OBJECT-TYPE
    SYNTAX    Integer32
    MAX-ACCESS    read-only
    STATUS    current
    DESCRIPTION    "This shows the capacity of expansion HDD slots of server blade6."
    ::= { blade6Capacity 9 }

blade6CapacityLED    OBJECT-TYPE
    SYNTAX    Integer32
    MAX-ACCESS    read-only
    STATUS    current
    DESCRIPTION    "This shows the capacity of count of LEDs of server blade6."
    ::= { blade6Capacity 10 }

blade6Settings    OBJECT IDENTIFIER ::= { blade6 3 } 

blade6SettingsBelongPartitionNum    OBJECT-TYPE
    SYNTAX    Integer32
    MAX-ACCESS    read-only
    STATUS    current
    DESCRIPTION    "This shows the partition number of server blade6."
    ::= { blade6Settings 1 }

blade6SettingsDetailHVMLicenceModel    OBJECT-TYPE
    SYNTAX    DisplayString (SIZE(0..40))
    MAX-ACCESS    read-only
    STATUS    current
    DESCRIPTION    "This shows the HVM licence of detailed server blade6 (model). "
    ::= { blade6Settings 2 }

blade6SettingsDetailHVMLicenceAvailableVersion    OBJECT-TYPE
    SYNTAX    DisplayString (SIZE(0..40))
    MAX-ACCESS    read-only
    STATUS    current
    DESCRIPTION    "This shows the HVM licence of detailed server blade6 (available version). "
    ::= { blade6Settings 3 }

blade6SettingsManagementPortIPAddress    OBJECT-TYPE
    SYNTAX    DisplayString (SIZE(0..40))
    MAX-ACCESS    read-only
    STATUS    current
    DESCRIPTION    "This shows the IP address of management port of server blade6."
    ::= { blade6Settings 4 }

blade6State    OBJECT IDENTIFIER ::= { blade6 4 } 

blade6StateSlotNum    OBJECT-TYPE
    SYNTAX    Integer32
    MAX-ACCESS    read-only
    STATUS    current
    DESCRIPTION    "This shows the number of installed slots of server blade6."
    ::= { blade6State 1 }

blade6StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade6."
    ::= { blade6State 2 }

blade6StateHealth    OBJECT-TYPE
    SYNTAX    INTEGER {
    normal (1),fail (2),unknown (3)
    }
    MAX-ACCESS    read-only
    STATUS    current
    DESCRIPTION    "This shows the health state of server blade6."
    ::= { blade6State 3 }

blade6StatePrimaly    OBJECT-TYPE
    SYNTAX    INTEGER {
    primary(1), non-primary(2),unknown(3)
    }
    MAX-ACCESS    read-only
    STATUS    current
    DESCRIPTION    "This shows the primary state of server blade6."
    ::= { blade6State 4 }

blade6StateCurrentVoltage    OBJECT-TYPE
    SYNTAX    Integer32
    UNITS    "0.1 V"
    MAX-ACCESS    read-only
    STATUS    current
    DESCRIPTION    "This shows the current voltage of server blade6."
    ::= { blade6State 5 }

blade6StateConsumptionCurrent    OBJECT-TYPE
    SYNTAX    Integer32
    UNITS    "0.1 A"
    MAX-ACCESS    read-only
    STATUS    current
    DESCRIPTION    "This shows the consumption current of server blade6."
    ::= { blade6State 6 }

blade6StatePowerConsumption    OBJECT-TYPE
    SYNTAX    Integer32
    UNITS    "W"
    MAX-ACCESS    read-only
    STATUS    current
    DESCRIPTION    "This shows the power consumption of server blade6."
    ::= { blade6State 7 }

blade6StateIntakeTemp    OBJECT-TYPE
    SYNTAX    INTEGER {
    normal (1), higher-warning (2), higher-error (3), lower-warning (4), unknown(5)
    }
    MAX-ACCESS    read-only
    STATUS    current
    DESCRIPTION    "This shows the state of intake temperature of server blade6."
    ::= { blade6State 8 }

blade6StateLEDTable    OBJECT-TYPE
    SYNTAX SEQUENCE OF blade6StateLEDEntry
    MAX-ACCESS not-accessible
    STATUS     current
    DESCRIPTION "This shows the table of LED of server blade6."
    ::= { blade6State 9 }

blade6StateLEDEntry    OBJECT-TYPE
    SYNTAX Blade6StateLEDEntry
    MAX-ACCESS not-accessible
    STATUS    current
    DESCRIPTION "This shows the entry of LED of server blade6."
    INDEX { blade6StateLEDIndex }
    ::= { blade6StateLEDTable 1 }

blade6StateLEDIndex    OBJECT-TYPE
    SYNTAX    Integer32
    MAX-ACCESS    read-only
    STATUS    current
    DESCRIPTION    "This shows the index of LED of server blade6."
    ::= { blade6StateLEDEntry 1 }

blade6StateLEDName    OBJECT-TYPE
    SYNTAX    DisplayString (SIZE(0..40))
    MAX-ACCESS    read-only
    STATUS    current
    DESCRIPTION    "This shows the name of LED of server blade6."
    ::= { blade6StateLEDEntry 2 }

blade6StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade6."
    ::= { blade6StateLEDEntry 3 }

blade6StateLEDColor    OBJECT-TYPE
    SYNTAX    INTEGER {
    blue (1),green (2),red (3),amber (4),unknown (5)
    }
    MAX-ACCESS    read-only
    STATUS    current
    DESCRIPTION    "This shows the color of LED of server blade6."
    ::= { blade6StateLEDEntry 4 }

Blade6StateLEDEntry ::= SEQUENCE {
    blade6StateLEDIndex
        Integer32,
    blade6StateLEDName
        DisplayString,
    blade6StateLEDState
        INTEGER,
    blade6StateLEDColor
        INTEGER
}

blade6StateOther    OBJECT IDENTIFIER ::= { blade6State 20 } 

blade6MaintMode    OBJECT-TYPE
    SYNTAX    INTEGER {
    Normal(1), CE-Maint-mode(2), User-Maint-mode(3), unknown(4)
    }
    MAX-ACCESS    read-only
    STATUS    current
    DESCRIPTION    "This shows the maintenance mode of server blade6."
    ::= { blade6StateOther 1 }

blade6Install    OBJECT IDENTIFIER ::= { blade6State 30 } 

blade6InsCPUSocketTable    OBJECT-TYPE
    SYNTAX SEQUENCE OF blade6InsCPUSocketEntry
    MAX-ACCESS not-accessible
    STATUS     current
    DESCRIPTION "This shows the table of CPU socket of server blade6."
    ::= { blade6Install 1 }

blade6InsCPUSocketEntry    OBJECT-TYPE
    SYNTAX Blade6InsCPUSocketEntry
    MAX-ACCESS not-accessible
    STATUS    current
    DESCRIPTION "This shows the entry of CPU socket of server blade6."
    INDEX { blade6InsCPUSocketIndex }
    ::= { blade6InsCPUSocketTable 1 }

blade6InsCPUSocketIndex    OBJECT-TYPE
    SYNTAX    Integer32
    MAX-ACCESS    read-only
    STATUS    current
    DESCRIPTION    "This shows the index of CPU socket of server blade6."
    ::= { blade6InsCPUSocketEntry 1 }

blade6InsCPUSocketNum    OBJECT-TYPE
    SYNTAX    Integer32
    MAX-ACCESS    read-only
    STATUS    current
    DESCRIPTION    "This shows the number of CPU sockets of server blade6."
    ::= { blade6InsCPUSocketEntry 2 }

blade6InsCPUSocketExist    OBJECT-TYPE
    SYNTAX    INTEGER {
    non-exist(1), exist(2), unknown(3)
    }
    MAX-ACCESS    read-only
    STATUS    current
    DESCRIPTION    "This shows the registrated state of CPU socket of server blade6."
    ::= { blade6InsCPUSocketEntry 3 }

blade6InsCPUSocketCPUName    OBJECT-TYPE
    SYNTAX    DisplayString (SIZE(0..40))
    MAX-ACCESS    read-only
    STATUS    current
    DESCRIPTION    "This shows the CPU name of CPU socket of server blade6."
    ::= { blade6InsCPUSocketEntry 4 }

blade6InsCPUSocketCPUFrequency    OBJECT-TYPE
    SYNTAX    Integer32
    UNITS    "MHz"
    MAX-ACCESS    read-only
    STATUS    current
    DESCRIPTION    "This shows the CPU frequency of CPU socket of server blade6."
    ::= { blade6InsCPUSocketEntry 5 }

blade6InsCPUSocketCPUStepping    OBJECT-TYPE
    SYNTAX    DisplayString 
    MAX-ACCESS    read-only
    STATUS    current
    DESCRIPTION    "This shows the CPU stepping of CPU socket of server blade6."
    ::= { blade6InsCPUSocketEntry 6 }

blade6InsCPUSocketCPUCoreNum    OBJECT-TYPE
    SYNTAX    Integer32
    MAX-ACCESS    read-only
    STATUS    current
    DESCRIPTION    "This shows the CPU core number of CPU socket of server blade6."
    ::= { blade6InsCPUSocketEntry 7 }

blade6InsCPUSocketCPUUpperLimitTemp    OBJECT-TYPE
    SYNTAX    Integer32
    UNITS    "0.1 degrees C"
    MAX-ACCESS    read-only
    STATUS    current
    DESCRIPTION    "This shows the maximum limited CPU temperature of server blade6."
    ::= { blade6InsCPUSocketEntry 8 }

blade6InsCPUSocketCPULowerLimitTemp    OBJECT-TYPE
    SYNTAX    Integer32
    UNITS    "0.1 degrees C"
    MAX-ACCESS    read-only
    STATUS    current
    DESCRIPTION    "This shows the minimum limited CPU temperature of server blade6."
    ::= { blade6InsCPUSocketEntry 9 }

blade6InsDIMMCapacity    OBJECT-TYPE
    SYNTAX    Integer32
    UNITS    "GB"
    MAX-ACCESS    read-only
    STATUS    current
    DESCRIPTION    "This shows the total amount of DIMM capacity of server blade6."
    ::= { blade6Install 2 }

Blade6InsCPUSocketEntry ::= SEQUENCE {
    blade6InsCPUSocketIndex
        Integer32,
    blade6InsCPUSocketNum
        Integer32,
    blade6InsCPUSocketExist
        INTEGER,
    blade6InsCPUSocketCPUName
        DisplayString,
    blade6InsCPUSocketCPUFrequency
        Integer32,
    blade6InsCPUSocketCPUStepping
        DisplayString,
    blade6InsCPUSocketCPUCoreNum
        Integer32,
    blade6InsCPUSocketCPUUpperLimitTemp
        Integer32,
    blade6InsCPUSocketCPULowerLimitTemp
        Integer32,
    blade6InsDIMMCapacity
        Integer32
}

blade6InsDIMMSlotTable    OBJECT-TYPE
    SYNTAX SEQUENCE OF blade6InsDIMMSlotEntry
    MAX-ACCESS not-accessible
    STATUS     current
    DESCRIPTION "This shows the table of DIMM slot of server blade6."
    ::= { blade6Install 3 }

blade6InsDIMMSlotEntry    OBJECT-TYPE
    SYNTAX Blade6InsDIMMSlotEntry
    MAX-ACCESS not-accessible
    STATUS    current
    DESCRIPTION "This shows the entry of DIMM slot of server blade6."
    INDEX { blade6InsDIMMSlotIndex }
    ::= { blade6InsDIMMSlotTable 1 }

blade6InsDIMMSlotIndex    OBJECT-TYPE
    SYNTAX    Integer32
    MAX-ACCESS    read-only
    STATUS    current
    DESCRIPTION    "This shows the index of DIMM slot of server blade6."
    ::= { blade6InsDIMMSlotEntry 1 }

blade6InsDIMMSlotExist    OBJECT-TYPE
    SYNTAX    INTEGER {
    non-exist(1), exist(2), unknown(3)
    }
    MAX-ACCESS    read-only
    STATUS    current
    DESCRIPTION    "This shows the registrated state of DIMM slot of server blade6."
    ::= { blade6InsDIMMSlotEntry 2 }

blade6InsDIMMSlotDIMMCapacity    OBJECT-TYPE
    SYNTAX    Integer32
    UNITS    "GB"
    MAX-ACCESS    read-only
    STATUS    current
    DESCRIPTION    "This shows the capacity of DIMM slots of server blade6."
    ::= { blade6InsDIMMSlotEntry 3 }

blade6InsDIMMSlotDIMMType    OBJECT-TYPE
    SYNTAX    DisplayString 
    MAX-ACCESS    read-only
    STATUS    current
    DESCRIPTION    "This shows the DIMM type of DIMM slot of server blade6."
    ::= { blade6InsDIMMSlotEntry 4 }

blade6InsDIMMSlotDIMMFrequency    OBJECT-TYPE
    SYNTAX    Integer32
    UNITS    "MHz"
    MAX-ACCESS    read-only
    STATUS    current
    DESCRIPTION    "This shows the DIMM frequency of DIMM slot of server blade6."
    ::= { blade6InsDIMMSlotEntry 5 }

blade6InsDIMMSlotDIMMCasLatency    OBJECT-TYPE
    SYNTAX    Integer32
    MAX-ACCESS    read-only
    STATUS    current
    DESCRIPTION    "This shows the DIMM cas latency of DIMM slot of server blade6."
    ::= { blade6InsDIMMSlotEntry 6 }

blade6InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade6."
    ::= { blade6InsDIMMSlotEntry 7 }

Blade6InsDIMMSlotEntry ::= SEQUENCE {
    blade6InsDIMMSlotIndex
        Integer32,
    blade6InsDIMMSlotExist
        INTEGER,
    blade6InsDIMMSlotDIMMCapacity
        Integer32,
    blade6InsDIMMSlotDIMMType
        DisplayString,
    blade6InsDIMMSlotDIMMFrequency
        Integer32,
    blade6InsDIMMSlotDIMMCasLatency
        Integer32,
    blade6InsDIMMSlotDIMMStatus
        INTEGER
}

blade6InsPCISlotTable    OBJECT-TYPE
    SYNTAX SEQUENCE OF blade6InsPCISlotEntry
    MAX-ACCESS not-accessible
    STATUS     current
    DESCRIPTION "This shows the table of PCI slot of server blade6."
    ::= { blade6Install 4 }

blade6InsPCISlotEntry    OBJECT-TYPE
    SYNTAX Blade6InsPCISlotEntry
    MAX-ACCESS not-accessible
    STATUS    current
    DESCRIPTION "This shows the entry of PCI slot of server blade6."
    INDEX { blade6InsPCISlotIndex }
    ::= { blade6InsPCISlotTable 1 }

blade6InsPCISlotIndex    OBJECT-TYPE
    SYNTAX    Integer32
    MAX-ACCESS    read-only
    STATUS    current
    DESCRIPTION    "This shows the index of PCI slot of server blade6."
    ::= { blade6InsPCISlotEntry 1 }

blade6InsPCISlotType    OBJECT-TYPE
    SYNTAX    DisplayString 
    MAX-ACCESS    read-only
    STATUS    current
    DESCRIPTION    "This shows the type of PCI slot of server blade6."
    ::= { blade6InsPCISlotEntry 2 }

blade6InsPCISlotExist    OBJECT-TYPE
    SYNTAX    INTEGER {
    non-exist(1), exist(2), unknown(3)
    }
    MAX-ACCESS    read-only
    STATUS    current
    DESCRIPTION    "This shows the registrated state of PCI slot of server blade6."
    ::= { blade6InsPCISlotEntry 3 }

blade6InsPCISlotPCIType    OBJECT-TYPE
    SYNTAX    DisplayString 
    MAX-ACCESS    read-only
    STATUS    current
    DESCRIPTION    "This shows the PCI type of PCI slot of server blade6."
    ::= { blade6InsPCISlotEntry 4 }

blade6InsPCISlotPCIProductName    OBJECT-TYPE
    SYNTAX    DisplayString 
    MAX-ACCESS    read-only
    STATUS    current
    DESCRIPTION    "This shows the PCI product name of PCI slot of server blade6."
    ::= { blade6InsPCISlotEntry 5 }

blade6InsPCISlotPCISerial    OBJECT-TYPE
    SYNTAX    DisplayString 
    MAX-ACCESS    read-only
    STATUS    current
    DESCRIPTION    "This shows the serial number of PCI slot of server blade6."
    ::= { blade6InsPCISlotEntry 6 }

blade6InsPCISlotPCIManufacturer    OBJECT-TYPE
    SYNTAX    DisplayString 
    MAX-ACCESS    read-only
    STATUS    current
    DESCRIPTION    "This shows the manufacturer of PCI slot of server blade6."
    ::= { blade6InsPCISlotEntry 7 }

blade6InsPCISlotNum    OBJECT-TYPE
    SYNTAX    Integer32
    MAX-ACCESS    read-only
    STATUS    current
    DESCRIPTION    "This shows the number of PCI slots of server blade6."
    ::= { blade6InsPCISlotEntry 8 }

Blade6InsPCISlotEntry ::= SEQUENCE {
    blade6InsPCISlotIndex
        Integer32,
    blade6InsPCISlotType
        DisplayString,
    blade6InsPCISlotExist
        INTEGER,
    blade6InsPCISlotPCIType
        DisplayString,
    blade6InsPCISlotPCIProductName
        DisplayString,
    blade6InsPCISlotPCISerial
        DisplayString,
    blade6InsPCISlotPCIManufacturer
        DisplayString,
    blade6InsPCISlotNum
        Integer32
}

blade6InsLOMTable    OBJECT-TYPE
    SYNTAX SEQUENCE OF blade6InsLOMEntry
    MAX-ACCESS not-accessible
    STATUS     current
    DESCRIPTION "This shows the table of onboard LAN of server blade6."
    ::= { blade6Install 5 }

blade6InsLOMEntry    OBJECT-TYPE
    SYNTAX Blade6InsLOMEntry
    MAX-ACCESS not-accessible
    STATUS    current
    DESCRIPTION "This shows the entry of onboard LAN of server blade6."
    INDEX { blade6InsLOMIndex }
    ::= { blade6InsLOMTable 1 }

blade6InsLOMIndex    OBJECT-TYPE
    SYNTAX    Integer32
    MAX-ACCESS    read-only
    STATUS    current
    DESCRIPTION    "This shows the index of onboard LAN of server blade6."
    ::= { blade6InsLOMEntry 1 }

blade6InsLOMType    OBJECT-TYPE
    SYNTAX    DisplayString 
    MAX-ACCESS    read-only
    STATUS    current
    DESCRIPTION    "This shows the type of onboard LAN of server blade6."
    ::= { blade6InsLOMEntry 2 }

blade6InsLOMLinkSpeed    OBJECT-TYPE
    SYNTAX    Integer32
    UNITS    "bps"
    MAX-ACCESS    read-only
    STATUS    current
    DESCRIPTION    "This shows the link speed of onboard LAN of server blade6."
    ::= { blade6InsLOMEntry 3 }

blade6InsLOMMAC    OBJECT-TYPE
    SYNTAX    DisplayString 
    MAX-ACCESS    read-only
    STATUS    current
    DESCRIPTION    "This shows the MAC address of onboard LAN of server blade6."
    ::= { blade6InsLOMEntry 4 }

blade6InsLOMLinkStatus    OBJECT-TYPE
    SYNTAX    INTEGER {
    up (1),down (2),unknown (3)
    }
    MAX-ACCESS    read-only
    STATUS    current
    DESCRIPTION    "This shows the link state of onboard LAN of server blade6."
    ::= { blade6InsLOMEntry 5 }

blade6InsLOMPortDivide    OBJECT-TYPE
    SYNTAX    INTEGER {
    possible (1),Impossible (2),unknown (3)
    }
    MAX-ACCESS    read-only
    STATUS    current
    DESCRIPTION    "This shows the port divide propriety of onboard LAN of server blade6."
    ::= { blade6InsLOMEntry 6 }

blade6InsLOMPortDivideNum    OBJECT-TYPE
    SYNTAX    Integer32
    MAX-ACCESS    read-only
    STATUS    current
    DESCRIPTION    "This shows the port divide number of onboard LAN of server blade6."
    ::= { blade6InsLOMEntry 7 }

Blade6InsLOMEntry ::= SEQUENCE {
    blade6InsLOMIndex
        Integer32,
    blade6InsLOMType
        DisplayString,
    blade6InsLOMLinkSpeed
        Integer32,
    blade6InsLOMMAC
        DisplayString,
    blade6InsLOMLinkStatus
        INTEGER,
    blade6InsLOMPortDivide
        INTEGER,
    blade6InsLOMPortDivideNum
        Integer32
}

blade6HDDSlotTable    OBJECT-TYPE
    SYNTAX SEQUENCE OF blade6HDDSlotEntry
    MAX-ACCESS not-accessible
    STATUS     current
    DESCRIPTION "This shows the table of HDD slot of server blade6."
    ::= { blade6Install 7 }

blade6HDDSlotEntry    OBJECT-TYPE
    SYNTAX Blade6HDDSlotEntry
    MAX-ACCESS not-accessible
    STATUS    current
    DESCRIPTION "This shows the entry of HDD slot of server blade6."
    INDEX { blade6HDDSlotIndex }
    ::= { blade6HDDSlotTable 1 }

blade6HDDSlotIndex    OBJECT-TYPE
    SYNTAX    Integer32
    MAX-ACCESS    read-only
    STATUS    current
    DESCRIPTION    "This shows the index of HDD slot of server blade6."
    ::= { blade6HDDSlotEntry 1 }

blade6HDDSlotNum    OBJECT-TYPE
    SYNTAX    Integer32
    MAX-ACCESS    read-only
    STATUS    current
    DESCRIPTION    "This shows the number of HDD slots of server blade6."
    ::= { blade6HDDSlotEntry 2 }

blade6HDDSlotExist    OBJECT-TYPE
    SYNTAX    INTEGER {
    non-exist(1), exist(2), unknown(3)
    }
    MAX-ACCESS    read-only
    STATUS    current
    DESCRIPTION    "This shows the registrated state of HDD slot of server blade6."
    ::= { blade6HDDSlotEntry 3 }

blade6HDDSlotHDDType    OBJECT-TYPE
    SYNTAX    DisplayString 
    MAX-ACCESS    read-only
    STATUS    current
    DESCRIPTION    "This shows the HDD type of HDD slot of server blade6."
    ::= { blade6HDDSlotEntry 4 }

blade6HDDSlotHDDProductName    OBJECT-TYPE
    SYNTAX    DisplayString 
    MAX-ACCESS    read-only
    STATUS    current
    DESCRIPTION    "This shows the HDD product name of HDD slot of server blade6."
    ::= { blade6HDDSlotEntry 5 }

blade6HDDSlotHDDModel    OBJECT-TYPE
    SYNTAX    DisplayString 
    MAX-ACCESS    read-only
    STATUS    current
    DESCRIPTION    "This shows the HDD model of HDD slot of server blade6."
    ::= { blade6HDDSlotEntry 6 }

blade6HDDSlotHDDSerialNum    OBJECT-TYPE
    SYNTAX    DisplayString 
    MAX-ACCESS    read-only
    STATUS    current
    DESCRIPTION    "This shows the HDD serial number of HDD slot of server blade6."
    ::= { blade6HDDSlotEntry 7 }

blade6HDDSlotHDDCapacity    OBJECT-TYPE
    SYNTAX    Integer32
    UNITS    "GB"
    MAX-ACCESS    read-only
    STATUS    current
    DESCRIPTION    "This shows the HDD capacity of HDD slots of server blade6."
    ::= { blade6HDDSlotEntry 8 }

blade6HDDSlotHDDRPM    OBJECT-TYPE
    SYNTAX    Integer32
    UNITS    "rpm"
    MAX-ACCESS    read-only
    STATUS    current
    DESCRIPTION    "This shows the HDD drive speed of HDD slot of server blade6."
    ::= { blade6HDDSlotEntry 9 }

blade6HDDSlotHDDStatePower    OBJECT-TYPE
    SYNTAX    INTEGER {
    poweroff (1), poweron (2), unknown (3)
    }
    MAX-ACCESS    read-only
    STATUS    current
    DESCRIPTION    "This shows the HDD power supply state of HDD slot of server blade6."
    ::= { blade6HDDSlotEntry 10 }

blade6HDDSlotHDDStateHealth    OBJECT-TYPE
    SYNTAX    INTEGER {
    normal (1),fail (2),unknown (3),rebuild (4)
    }
    MAX-ACCESS    read-only
    STATUS    current
    DESCRIPTION    "This shows the HDD health state of HDD slot of server blade6."
    ::= { blade6HDDSlotEntry 11 }

blade6HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade6(activity)."
    ::= { blade6HDDSlotEntry 12 }

blade6HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade6(status)."
    ::= { blade6HDDSlotEntry 13 }

blade6HDDSlotHDDFWInfoName    OBJECT-TYPE
    SYNTAX    DisplayString 
    MAX-ACCESS    read-only
    STATUS    current
    DESCRIPTION    "This shows the HDD firmware name of HDD slot of server blade6."
    ::= { blade6HDDSlotEntry 20 }

blade6HDDSlotHDDFWInfoCurrentVer    OBJECT-TYPE
    SYNTAX    DisplayString 
    MAX-ACCESS    read-only
    STATUS    current
    DESCRIPTION    "This shows the HDD firmware current version of HDD slot of server blade6."
    ::= { blade6HDDSlotEntry 21 }

blade6HDDSlotHDDFWInfoNextVer    OBJECT-TYPE
    SYNTAX    DisplayString 
    MAX-ACCESS    read-only
    STATUS    current
    DESCRIPTION    "This shows the HDD firmware next version of HDD slot of server blade6."
    ::= { blade6HDDSlotEntry 22 }

Blade6HDDSlotEntry ::= SEQUENCE {
    blade6HDDSlotIndex
        Integer32,
    blade6HDDSlotNum
        Integer32,
    blade6HDDSlotExist
        INTEGER,
    blade6HDDSlotHDDType
        DisplayString,
    blade6HDDSlotHDDProductName
        DisplayString,
    blade6HDDSlotHDDModel
        DisplayString,
    blade6HDDSlotHDDSerialNum
        DisplayString,
    blade6HDDSlotHDDCapacity
        Integer32,
    blade6HDDSlotHDDRPM
        Integer32,
    blade6HDDSlotHDDStatePower
        INTEGER,
    blade6HDDSlotHDDStateHealth
        INTEGER,
    blade6HDDSlotHDDStateLEDACT
        INTEGER,
    blade6HDDSlotHDDStateLEDSTS
        INTEGER,
    blade6HDDSlotHDDFWInfoName
        DisplayString,
    blade6HDDSlotHDDFWInfoCurrentVer
        DisplayString,
    blade6HDDSlotHDDFWInfoNextVer
        DisplayString
}

blade6ExpansionHDDSlotTable    OBJECT-TYPE
    SYNTAX SEQUENCE OF blade6ExpansionHDDSlotEntry
    MAX-ACCESS not-accessible
    STATUS     current
    DESCRIPTION "This shows the table of expansion HDD slot of server blade6."
    ::= { blade6Install 8 }

blade6ExpansionHDDSlotEntry    OBJECT-TYPE
    SYNTAX Blade6ExpansionHDDSlotEntry
    MAX-ACCESS not-accessible
    STATUS    current
    DESCRIPTION "This shows the entry of expansion HDD slot of server blade6."
    INDEX { blade6ExpansionHDDSlotIndex }
    ::= { blade6ExpansionHDDSlotTable 1 }

blade6ExpansionHDDSlotIndex    OBJECT-TYPE
    SYNTAX    Integer32
    MAX-ACCESS    read-only
    STATUS    current
    DESCRIPTION    "This shows the index of expansion HDD slot of server blade6."
    ::= { blade6ExpansionHDDSlotEntry 1 }

blade6ExpansionHDDSlotNum    OBJECT-TYPE
    SYNTAX    Integer32
    MAX-ACCESS    read-only
    STATUS    current
    DESCRIPTION    "This shows the number of expansion HDD slots of server blade6."
    ::= { blade6ExpansionHDDSlotEntry 2 }

blade6ExpansionHDDSlotExist    OBJECT-TYPE
    SYNTAX    INTEGER {
    non-exist(1), exist(2), unknown(3)
    }
    MAX-ACCESS    read-only
    STATUS    current
    DESCRIPTION    "This shows the registrated state of expansion HDD slot of server blade6."
    ::= { blade6ExpansionHDDSlotEntry 3 }

blade6ExpansionHDDSlotHDDType    OBJECT-TYPE
    SYNTAX    DisplayString 
    MAX-ACCESS    read-only
    STATUS    current
    DESCRIPTION    "This shows the HDD type of expansion HDD slot of server blade6."
    ::= { blade6ExpansionHDDSlotEntry 4 }

blade6ExpansionHDDSlotHDDProductName    OBJECT-TYPE
    SYNTAX    DisplayString 
    MAX-ACCESS    read-only
    STATUS    current
    DESCRIPTION    "This shows the HDD product name of expansion HDD slot of server blade6."
    ::= { blade6ExpansionHDDSlotEntry 5 }

blade6ExpansionHDDSlotHDDModel    OBJECT-TYPE
    SYNTAX    DisplayString 
    MAX-ACCESS    read-only
    STATUS    current
    DESCRIPTION    "This shows the HDD model of expansion HDD slot of server blade6."
    ::= { blade6ExpansionHDDSlotEntry 6 }

blade6ExpansionHDDSlotHDDSerialNum    OBJECT-TYPE
    SYNTAX    DisplayString 
    MAX-ACCESS    read-only
    STATUS    current
    DESCRIPTION    "This shows the HDD serial number of expansion HDD slot of server blade6."
    ::= { blade6ExpansionHDDSlotEntry 7 }

blade6ExpansionHDDSlotHDDCapacity    OBJECT-TYPE
    SYNTAX    Integer32
    UNITS    "GB"
    MAX-ACCESS    read-only
    STATUS    current
    DESCRIPTION    "This shows the HDD capacity of expansion HDD slots of server blade6."
    ::= { blade6ExpansionHDDSlotEntry 8 }

blade6ExpansionHDDSlotHDDRPM    OBJECT-TYPE
    SYNTAX    Integer32
    UNITS    "rpm"
    MAX-ACCESS    read-only
    STATUS    current
    DESCRIPTION    "This shows the HDD drive speed of expansion HDD slot of server blade6."
    ::= { blade6ExpansionHDDSlotEntry 9 }

blade6ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade6."
    ::= { blade6ExpansionHDDSlotEntry 10 }

blade6ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade6."
    ::= { blade6ExpansionHDDSlotEntry 11 }

blade6ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade6(activity)."
    ::= { blade6ExpansionHDDSlotEntry 12 }

blade6ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade6(status)."
    ::= { blade6ExpansionHDDSlotEntry 13 }

blade6ExpansionHDDSlotHDDFWInfoName    OBJECT-TYPE
    SYNTAX    DisplayString 
    MAX-ACCESS    read-only
    STATUS    current
    DESCRIPTION    "This shows the HDD firmware name of expansion HDD slot of server blade6."
    ::= { blade6ExpansionHDDSlotEntry 20 }

blade6ExpansionHDDSlotHDDFWInfoCurrentVer    OBJECT-TYPE
    SYNTAX    DisplayString 
    MAX-ACCESS    read-only
    STATUS    current
    DESCRIPTION    "This shows the HDD firmware current version of expansion HDD slot of server blade6."
    ::= { blade6ExpansionHDDSlotEntry 21 }

blade6ExpansionHDDSlotHDDFWInfoNextVer    OBJECT-TYPE
    SYNTAX    DisplayString 
    MAX-ACCESS    read-only
    STATUS    current
    DESCRIPTION    "This shows the HDD firmware next version of expansion HDD slot of server blade6."
    ::= { blade6ExpansionHDDSlotEntry 22 }

Blade6ExpansionHDDSlotEntry ::= SEQUENCE {
    blade6ExpansionHDDSlotIndex
        Integer32,
    blade6ExpansionHDDSlotNum
        Integer32,
    blade6ExpansionHDDSlotExist
        INTEGER,
    blade6ExpansionHDDSlotHDDType
        DisplayString,
    blade6ExpansionHDDSlotHDDProductName
        DisplayString,
    blade6ExpansionHDDSlotHDDModel
        DisplayString,
    blade6ExpansionHDDSlotHDDSerialNum
        DisplayString,
    blade6ExpansionHDDSlotHDDCapacity
        Integer32,
    blade6ExpansionHDDSlotHDDRPM
        Integer32,
    blade6ExpansionHDDSlotHDDStatePower
        INTEGER,
    blade6ExpansionHDDSlotHDDStateHealth
        INTEGER,
    blade6ExpansionHDDSlotHDDStateLEDACT
        INTEGER,
    blade6ExpansionHDDSlotHDDStateLEDSTS
        INTEGER,
    blade6ExpansionHDDSlotHDDFWInfoName
        DisplayString,
    blade6ExpansionHDDSlotHDDFWInfoCurrentVer
        DisplayString,
    blade6ExpansionHDDSlotHDDFWInfoNextVer
        DisplayString
}

blade6VoltageSensorTable    OBJECT-TYPE
    SYNTAX SEQUENCE OF blade6VoltageSensorEntry
    MAX-ACCESS not-accessible
    STATUS     current
    DESCRIPTION "This shows the table of voltage sensor of server blade6."
    ::= { blade6State 40 }

blade6VoltageSensorEntry    OBJECT-TYPE
    SYNTAX Blade6VoltageSensorEntry
    MAX-ACCESS not-accessible
    STATUS    current
    DESCRIPTION "This shows the entry of voltage sensor of server blade6."
    INDEX { blade6VoltageSensorIndex }
    ::= { blade6VoltageSensorTable 1 }

blade6VoltageSensorIndex    OBJECT-TYPE
    SYNTAX    Integer32
    MAX-ACCESS    read-only
    STATUS    current
    DESCRIPTION    "This shows the index of voltage sensor of server blade6."
    ::= { blade6VoltageSensorEntry 1 }

blade6VoltageSensorName    OBJECT-TYPE
    SYNTAX    DisplayString 
    MAX-ACCESS    read-only
    STATUS    current
    DESCRIPTION    "This shows the voltage sensor name of server blade6."
    ::= { blade6VoltageSensorEntry 2 }

blade6VoltageSensorValue    OBJECT-TYPE
    SYNTAX    Integer32
    UNITS    "0.1 V"
    MAX-ACCESS    read-only
    STATUS    current
    DESCRIPTION    "This shows the voltage sensor value of server blade6."
    ::= { blade6VoltageSensorEntry 3 }

blade6VoltageSensorValid    OBJECT-TYPE
    SYNTAX    INTEGER {
    invalid (1),valid (2),unknown (3)
    }
    MAX-ACCESS    read-only
    STATUS    current
    DESCRIPTION    "This shows the validity of voltage sensor value of server blade6."
    ::= { blade6VoltageSensorEntry 4 }

Blade6VoltageSensorEntry ::= SEQUENCE {
    blade6VoltageSensorIndex
        Integer32,
    blade6VoltageSensorName
        DisplayString,
    blade6VoltageSensorValue
        Integer32,
    blade6VoltageSensorValid
        INTEGER
}

blade6TempSensorTable    OBJECT-TYPE
    SYNTAX SEQUENCE OF blade6TempSensorEntry
    MAX-ACCESS not-accessible
    STATUS     current
    DESCRIPTION "This shows the table of temperature sensor of server blade6."
    ::= { blade6State 41 }

blade6TempSensorEntry    OBJECT-TYPE
    SYNTAX Blade6TempSensorEntry
    MAX-ACCESS not-accessible
    STATUS    current
    DESCRIPTION "This shows the entry of temperature sensor of server blade6."
    INDEX { blade6TempSensorIndex }
    ::= { blade6TempSensorTable 1 }

blade6TempSensorIndex    OBJECT-TYPE
    SYNTAX    Integer32
    MAX-ACCESS    read-only
    STATUS    current
    DESCRIPTION    "This shows the index of temperature sensor of server blade6."
    ::= { blade6TempSensorEntry 1 }

blade6TempSensorName    OBJECT-TYPE
    SYNTAX    DisplayString 
    MAX-ACCESS    read-only
    STATUS    current
    DESCRIPTION    "This shows the temperature sensor name of server blade6."
    ::= { blade6TempSensorEntry 2 }

blade6TempSensorValue    OBJECT-TYPE
    SYNTAX    Integer32
    UNITS    "0.1 degrees C"
    MAX-ACCESS    read-only
    STATUS    current
    DESCRIPTION    "This shows the temperature sensor value of server blade6."
    ::= { blade6TempSensorEntry 3 }

blade6TempSensorValid    OBJECT-TYPE
    SYNTAX    INTEGER {
    invalid (1),valid (2),unknown (3)
    }
    MAX-ACCESS    read-only
    STATUS    current
    DESCRIPTION    "This shows the validity of temperature sensor value of server blade6."
    ::= { blade6TempSensorEntry 4 }

Blade6TempSensorEntry ::= SEQUENCE {
    blade6TempSensorIndex
        Integer32,
    blade6TempSensorName
        DisplayString,
    blade6TempSensorValue
        Integer32,
    blade6TempSensorValid
        INTEGER
}

blade6FWInfo    OBJECT IDENTIFIER ::= { blade6 5 } 

blade6FWInfoTotalCurrentVer    OBJECT-TYPE
    SYNTAX    DisplayString (SIZE(0..40))
    MAX-ACCESS    read-only
    STATUS    current
    DESCRIPTION    "This shows the total current version of firmware of server blade6."
    ::= { blade6FWInfo 1 }

blade6FWInfoTotalNextVer    OBJECT-TYPE
    SYNTAX    DisplayString (SIZE(0..40))
    MAX-ACCESS    read-only
    STATUS    current
    DESCRIPTION    "This shows the total next version of firmware of server blade6."
    ::= { blade6FWInfo 2 }

blade6FWInfoTable    OBJECT-TYPE
    SYNTAX SEQUENCE OF blade6FWInfoEntry
    MAX-ACCESS not-accessible
    STATUS     current
    DESCRIPTION "This shows the table of firmware information of server blade6."
    ::= { blade6FWInfo 3 }

blade6FWInfoEntry    OBJECT-TYPE
    SYNTAX Blade6FWInfoEntry
    MAX-ACCESS not-accessible
    STATUS    current
    DESCRIPTION "This shows the entry of firmware information of server blade6."
    INDEX { blade6FWInfoIndex }
    ::= { blade6FWInfoTable 1 }

blade6FWInfoIndex    OBJECT-TYPE
    SYNTAX    Integer32
    MAX-ACCESS    read-only
    STATUS    current
    DESCRIPTION    "This shows the index of firmware information of server blade6."
    ::= { blade6FWInfoEntry 1 }

blade6FWInfoName    OBJECT-TYPE
    SYNTAX    DisplayString (SIZE(0..40))
    MAX-ACCESS    read-only
    STATUS    current
    DESCRIPTION    "This shows the firmware name of server blade6."
    ::= { blade6FWInfoEntry 2 }

blade6FWCurrentVer    OBJECT-TYPE
    SYNTAX    DisplayString (SIZE(0..40))
    MAX-ACCESS    read-only
    STATUS    current
    DESCRIPTION    "This shows the firmware current version of server blade6."
    ::= { blade6FWInfoEntry 3 }

blade6FWInfoNextVer    OBJECT-TYPE
    SYNTAX    DisplayString (SIZE(0..40))
    MAX-ACCESS    read-only
    STATUS    current
    DESCRIPTION    "This shows the firmware next version of server blade6."
    ::= { blade6FWInfoEntry 4 }

blade6FWInfoHVMCurrentVer    OBJECT-TYPE
    SYNTAX    DisplayString (SIZE(0..40))
    MAX-ACCESS    read-only
    STATUS    current
    DESCRIPTION    "This shows the HVM current version of server blade6."
    ::= { blade6FWInfo 4 }

blade6FWInfoHVMNextVer    OBJECT-TYPE
    SYNTAX    DisplayString (SIZE(0..40))
    MAX-ACCESS    read-only
    STATUS    current
    DESCRIPTION    "This shows the HVM next version of server blade6."
    ::= { blade6FWInfo 5 }

Blade6FWInfoEntry ::= SEQUENCE {
    blade6FWInfoIndex
        Integer32,
    blade6FWInfoName
        DisplayString,
    blade6FWCurrentVer
        DisplayString,
    blade6FWInfoNextVer
        DisplayString,
    blade6FWInfoHVMCurrentVer
        DisplayString,
    blade6FWInfoHVMNextVer
        DisplayString
}

blade7    OBJECT IDENTIFIER ::= { blade 7 } 

blade7BasicInfo    OBJECT IDENTIFIER ::= { blade7 1 } 

blade7InfoProductName    OBJECT-TYPE
    SYNTAX    DisplayString (SIZE(0..40))
    MAX-ACCESS    read-only
    STATUS    current
    DESCRIPTION    "This shows the product name of server blade7."
    ::= { blade7BasicInfo 1 }

blade7InfoModel    OBJECT-TYPE
    SYNTAX    DisplayString (SIZE(0..40))
    MAX-ACCESS    read-only
    STATUS    current
    DESCRIPTION    "This shows the model name of server blade7."
    ::= { blade7BasicInfo 2 }

blade7InfoSerialNum    OBJECT-TYPE
    SYNTAX    DisplayString (SIZE(0..40))
    MAX-ACCESS    read-only
    STATUS    current
    DESCRIPTION    "This shows the serial number of server blade7."
    ::= { blade7BasicInfo 3 }

blade7InfoProductVersion    OBJECT-TYPE
    SYNTAX    DisplayString (SIZE(0..40))
    MAX-ACCESS    read-only
    STATUS    current
    DESCRIPTION    "This shows the product version of server blade7."
    ::= { blade7BasicInfo 4 }

blade7InfoProductManufacturer    OBJECT-TYPE
    SYNTAX    DisplayString (SIZE(0..40))
    MAX-ACCESS    read-only
    STATUS    current
    DESCRIPTION    "This shows the product manufacturer of server blade7."
    ::= { blade7BasicInfo 5 }

blade7InfoBoardProductName    OBJECT-TYPE
    SYNTAX    DisplayString (SIZE(0..40))
    MAX-ACCESS    read-only
    STATUS    current
    DESCRIPTION    "This shows the board product name of server blade7."
    ::= { blade7BasicInfo 7 }

blade7InfoBoardSerialNum    OBJECT-TYPE
    SYNTAX    DisplayString (SIZE(0..40))
    MAX-ACCESS    read-only
    STATUS    current
    DESCRIPTION    "This shows the board serial number of server blade7."
    ::= { blade7BasicInfo 8 }

blade7InfoBoardManufacturer    OBJECT-TYPE
    SYNTAX    DisplayString (SIZE(0..40))
    MAX-ACCESS    read-only
    STATUS    current
    DESCRIPTION    "This shows the board manufacturer of server blade7."
    ::= { blade7BasicInfo 9 }

blade7InfoUUID    OBJECT-TYPE
    SYNTAX    DisplayString (SIZE(0..40))
    MAX-ACCESS    read-only
    STATUS    current
    DESCRIPTION    "This shows UUID(universal Unique ID) of server blade7."
    ::= { blade7BasicInfo 10 }

blade7InfoLogicalPartitionSupport    OBJECT-TYPE
    SYNTAX    INTEGER {
    not-support(1), support(2),unknown(3)
    }
    MAX-ACCESS    read-only
    STATUS    current
    DESCRIPTION    "This shows whether the server blade7 supports HVM or not of server blade1."
    ::= { blade7BasicInfo 11 }

blade7InfoRemoteKVMSupport    OBJECT-TYPE
    SYNTAX    INTEGER {
    not-support(1), support(2),unknown(3)
    }
    MAX-ACCESS    read-only
    STATUS    current
    DESCRIPTION    "This shows whether the server blade7 supports remote KVM or not of server blade1."
    ::= { blade7BasicInfo 12 }

blade7InfoSpec    OBJECT IDENTIFIER ::= { blade7BasicInfo 20 } 

blade7SpecInputCurrentType    OBJECT-TYPE
    SYNTAX    INTEGER {
    ac(1),dc(2),unknown(3)
    }
    MAX-ACCESS    read-only
    STATUS    current
    DESCRIPTION    "This shows the currency type of server blade7."
    ::= { blade7InfoSpec 1 }

blade7SpecRateVoltage    OBJECT-TYPE
    SYNTAX    Integer32
    UNITS    "0.1 V"
    MAX-ACCESS    read-only
    STATUS    current
    DESCRIPTION    "This shows the rated voltage of server blade7."
    ::= { blade7InfoSpec 2 }

blade7SpecConsumptionCurrent    OBJECT-TYPE
    SYNTAX    Integer32
    UNITS    "0.1 A"
    MAX-ACCESS    read-only
    STATUS    current
    DESCRIPTION    "This shows the consumption current of server blade7."
    ::= { blade7InfoSpec 3 }

blade7SpecPowerConsumption    OBJECT-TYPE
    SYNTAX    Integer32
    UNITS    "W"
    MAX-ACCESS    read-only
    STATUS    current
    DESCRIPTION    "This shows the power consumption of server blade7."
    ::= { blade7InfoSpec 4 }

blade7SpecMass    OBJECT-TYPE
    SYNTAX    Integer32
    UNITS    "0.1 kg"
    MAX-ACCESS    read-only
    STATUS    current
    DESCRIPTION    "This shows the weight of server blade7."
    ::= { blade7InfoSpec 5 }

blade7InfoUpperLimitIntakeTemp    OBJECT-TYPE
    SYNTAX    Integer32
    UNITS    "0.1 degrees C"
    MAX-ACCESS    read-only
    STATUS    current
    DESCRIPTION    "This shows the maximum limited intake temperature of server blade7."
    ::= { blade7InfoSpec 6 }

blade7InfoLowerLimitIntakeTemp    OBJECT-TYPE
    SYNTAX    Integer32
    UNITS    "0.1 degrees C"
    MAX-ACCESS    read-only
    STATUS    current
    DESCRIPTION    "This shows the minimum limited intake temperature of server blade7."
    ::= { blade7InfoSpec 7 }

blade7SpecSize    OBJECT-TYPE
    SYNTAX    DisplayString (SIZE(0..40))
    MAX-ACCESS    read-only
    STATUS    current
    DESCRIPTION    "This shows the size of server blade7."
    ::= { blade7InfoSpec 8 }

blade7SpecOccupySlots    OBJECT-TYPE
    SYNTAX    Integer32
    MAX-ACCESS    read-only
    STATUS    current
    DESCRIPTION    "This shows the dedicated number of slots of server blade7."
    ::= { blade7InfoSpec 9 }

blade7SpecExpansionBladeSlot    OBJECT-TYPE
    SYNTAX    Integer32
    MAX-ACCESS    read-only
    STATUS    current
    DESCRIPTION    "This shows the number of slots of expansion blade of server blade7."
    ::= { blade7InfoSpec 10 }

blade7InfoExpansionBladeTable    OBJECT-TYPE
    SYNTAX SEQUENCE OF blade7InfoExpansionBladeEntry
    MAX-ACCESS not-accessible
    STATUS     current
    DESCRIPTION "This shows the table of expansion blade slot of server blade7."
    ::= { blade7BasicInfo 30 }

blade7InfoExpansionBladeEntry    OBJECT-TYPE
    SYNTAX Blade7InfoExpansionBladeEntry
    MAX-ACCESS not-accessible
    STATUS    current
    DESCRIPTION "This shows the entry of expansion blade slot of server blade7."
    INDEX { blade7InfoExpansionBladeIndex }
    ::= { blade7InfoExpansionBladeTable 1 }

blade7InfoExpansionBladeIndex    OBJECT-TYPE
    SYNTAX    Integer32
    MAX-ACCESS    read-only
    STATUS    current
    DESCRIPTION    "This shows the index of expansion blade slot of server blade7."
    ::= { blade7InfoExpansionBladeEntry 1 }

blade7InfoExpansionBladeExist    OBJECT-TYPE
    SYNTAX    INTEGER {
    non-exist(1), exist(2), unknown(3)
    }
    MAX-ACCESS    read-only
    STATUS    current
    DESCRIPTION    "This shows the registrated state of expansion blade of server blade7."
    ::= { blade7InfoExpansionBladeEntry 2 }

blade7InfoExpansionBladeProductName    OBJECT-TYPE
    SYNTAX    DisplayString (SIZE(0..40))
    MAX-ACCESS    read-only
    STATUS    current
    DESCRIPTION    "This shows the product name of expansion blade of server blade7."
    ::= { blade7InfoExpansionBladeEntry 3 }

blade7InfoExpansionBladeModel    OBJECT-TYPE
    SYNTAX    DisplayString (SIZE(0..40))
    MAX-ACCESS    read-only
    STATUS    current
    DESCRIPTION    "This shows the model name of expansion blade of server blade7."
    ::= { blade7InfoExpansionBladeEntry 4 }

blade7InfoExpansionBladeSerialNum    OBJECT-TYPE
    SYNTAX    DisplayString (SIZE(0..40))
    MAX-ACCESS    read-only
    STATUS    current
    DESCRIPTION    "This shows the serial number of expansion blade of server blade7."
    ::= { blade7InfoExpansionBladeEntry 5 }

blade7InfoExpansionBladeProductVersion    OBJECT-TYPE
    SYNTAX    DisplayString (SIZE(0..40))
    MAX-ACCESS    read-only
    STATUS    current
    DESCRIPTION    "This shows the product version of expansion blade of server blade7."
    ::= { blade7InfoExpansionBladeEntry 6 }

blade7InfoExpansionBladeProductManufacturer    OBJECT-TYPE
    SYNTAX    DisplayString (SIZE(0..40))
    MAX-ACCESS    read-only
    STATUS    current
    DESCRIPTION    "This shows the product manufacturer of expansion blade of server blade7."
    ::= { blade7InfoExpansionBladeEntry 7 }

blade7InfoExpansionBladeBoardProductName    OBJECT-TYPE
    SYNTAX    DisplayString (SIZE(0..40))
    MAX-ACCESS    read-only
    STATUS    current
    DESCRIPTION    "This shows the board product name of expansion blade of server blade7."
    ::= { blade7InfoExpansionBladeEntry 9 }

blade7InfoExpansionBladeBoardSerialNum    OBJECT-TYPE
    SYNTAX    DisplayString (SIZE(0..40))
    MAX-ACCESS    read-only
    STATUS    current
    DESCRIPTION    "This shows the board serial number of expansion blade of server blade7."
    ::= { blade7InfoExpansionBladeEntry 10 }

blade7InfoExpansionBladeBoardManufacturer    OBJECT-TYPE
    SYNTAX    DisplayString (SIZE(0..40))
    MAX-ACCESS    read-only
    STATUS    current
    DESCRIPTION    "This shows the board manufacturer of expansion blade of server blade7."
    ::= { blade7InfoExpansionBladeEntry 11 }

Blade7InfoExpansionBladeEntry ::= SEQUENCE {
    blade7InfoExpansionBladeIndex
        Integer32,
    blade7InfoExpansionBladeExist
        INTEGER,
    blade7InfoExpansionBladeProductName
        DisplayString,
    blade7InfoExpansionBladeModel
        DisplayString,
    blade7InfoExpansionBladeSerialNum
        DisplayString,
    blade7InfoExpansionBladeProductVersion
        DisplayString,
    blade7InfoExpansionBladeProductManufacturer
        DisplayString,
    blade7InfoExpansionBladeBoardProductName
        DisplayString,
    blade7InfoExpansionBladeBoardSerialNum
        DisplayString,
    blade7InfoExpansionBladeBoardManufacturer
        DisplayString
}

blade7Capacity    OBJECT IDENTIFIER ::= { blade7 2 } 

blade7CapacityCPUSocket    OBJECT-TYPE
    SYNTAX    Integer32
    MAX-ACCESS    read-only
    STATUS    current
    DESCRIPTION    "This shows the capacity of CPU sockets of server blade7."
    ::= { blade7Capacity 1 }

blade7CapacityDIMMSlot    OBJECT-TYPE
    SYNTAX    Integer32
    MAX-ACCESS    read-only
    STATUS    current
    DESCRIPTION    "This shows the capacity of DIMM slots of server blade7."
    ::= { blade7Capacity 2 }

blade7CapacityPCISlot    OBJECT-TYPE
    SYNTAX    Integer32
    MAX-ACCESS    read-only
    STATUS    current
    DESCRIPTION    "This shows the capacity of PCI slots of server blade7."
    ::= { blade7Capacity 3 }

blade7CapacityLOM    OBJECT-TYPE
    SYNTAX    Integer32
    MAX-ACCESS    read-only
    STATUS    current
    DESCRIPTION    "This shows the capacity of onboard LAN ports of server blade7."
    ::= { blade7Capacity 4 }

blade7CapacityFan    OBJECT-TYPE
    SYNTAX    Integer32
    MAX-ACCESS    read-only
    STATUS    current
    DESCRIPTION    "This shows the capacity of onboard fans of server blade7."
    ::= { blade7Capacity 5 }

blade7CapacityHDDSlot    OBJECT-TYPE
    SYNTAX    Integer32
    MAX-ACCESS    read-only
    STATUS    current
    DESCRIPTION    "This shows the capacity of HDD slots of server blade7."
    ::= { blade7Capacity 6 }

blade7CapacityVoltageSensor    OBJECT-TYPE
    SYNTAX    Integer32
    MAX-ACCESS    read-only
    STATUS    current
    DESCRIPTION    "This shows the capacity of voltage sensors of blade7."
    ::= { blade7Capacity 7 }

blade7CapacityTempSensor    OBJECT-TYPE
    SYNTAX    Integer32
    MAX-ACCESS    read-only
    STATUS    current
    DESCRIPTION    "This shows the capacity of temperature sensors of blade7."
    ::= { blade7Capacity 8 }

blade7CapacityExpansionHDDSlot    OBJECT-TYPE
    SYNTAX    Integer32
    MAX-ACCESS    read-only
    STATUS    current
    DESCRIPTION    "This shows the capacity of expansion HDD slots of server blade7."
    ::= { blade7Capacity 9 }

blade7CapacityLED    OBJECT-TYPE
    SYNTAX    Integer32
    MAX-ACCESS    read-only
    STATUS    current
    DESCRIPTION    "This shows the capacity of count of LEDs of server blade7."
    ::= { blade7Capacity 10 }

blade7Settings    OBJECT IDENTIFIER ::= { blade7 3 } 

blade7SettingsBelongPartitionNum    OBJECT-TYPE
    SYNTAX    Integer32
    MAX-ACCESS    read-only
    STATUS    current
    DESCRIPTION    "This shows the partition number of server blade7."
    ::= { blade7Settings 1 }

blade7SettingsDetailHVMLicenceModel    OBJECT-TYPE
    SYNTAX    DisplayString (SIZE(0..40))
    MAX-ACCESS    read-only
    STATUS    current
    DESCRIPTION    "This shows the HVM licence of detailed server blade7 (model). "
    ::= { blade7Settings 2 }

blade7SettingsDetailHVMLicenceAvailableVersion    OBJECT-TYPE
    SYNTAX    DisplayString (SIZE(0..40))
    MAX-ACCESS    read-only
    STATUS    current
    DESCRIPTION    "This shows the HVM licence of detailed server blade7 (available version). "
    ::= { blade7Settings 3 }

blade7SettingsManagementPortIPAddress    OBJECT-TYPE
    SYNTAX    DisplayString (SIZE(0..40))
    MAX-ACCESS    read-only
    STATUS    current
    DESCRIPTION    "This shows the IP address of management port of server blade7."
    ::= { blade7Settings 4 }

blade7State    OBJECT IDENTIFIER ::= { blade7 4 } 

blade7StateSlotNum    OBJECT-TYPE
    SYNTAX    Integer32
    MAX-ACCESS    read-only
    STATUS    current
    DESCRIPTION    "This shows the number of installed slots of server blade7."
    ::= { blade7State 1 }

blade7StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade7."
    ::= { blade7State 2 }

blade7StateHealth    OBJECT-TYPE
    SYNTAX    INTEGER {
    normal (1),fail (2),unknown (3)
    }
    MAX-ACCESS    read-only
    STATUS    current
    DESCRIPTION    "This shows the health state of server blade7."
    ::= { blade7State 3 }

blade7StatePrimaly    OBJECT-TYPE
    SYNTAX    INTEGER {
    primary(1), non-primary(2),unknown(3)
    }
    MAX-ACCESS    read-only
    STATUS    current
    DESCRIPTION    "This shows the primary state of server blade7."
    ::= { blade7State 4 }

blade7StateCurrentVoltage    OBJECT-TYPE
    SYNTAX    Integer32
    UNITS    "0.1 V"
    MAX-ACCESS    read-only
    STATUS    current
    DESCRIPTION    "This shows the current voltage of server blade7."
    ::= { blade7State 5 }

blade7StateConsumptionCurrent    OBJECT-TYPE
    SYNTAX    Integer32
    UNITS    "0.1 A"
    MAX-ACCESS    read-only
    STATUS    current
    DESCRIPTION    "This shows the consumption current of server blade7."
    ::= { blade7State 6 }

blade7StatePowerConsumption    OBJECT-TYPE
    SYNTAX    Integer32
    UNITS    "W"
    MAX-ACCESS    read-only
    STATUS    current
    DESCRIPTION    "This shows the power consumption of server blade7."
    ::= { blade7State 7 }

blade7StateIntakeTemp    OBJECT-TYPE
    SYNTAX    INTEGER {
    normal (1), higher-warning (2), higher-error (3), lower-warning (4), unknown(5)
    }
    MAX-ACCESS    read-only
    STATUS    current
    DESCRIPTION    "This shows the state of intake temperature of server blade7."
    ::= { blade7State 8 }

blade7StateLEDTable    OBJECT-TYPE
    SYNTAX SEQUENCE OF blade7StateLEDEntry
    MAX-ACCESS not-accessible
    STATUS     current
    DESCRIPTION "This shows the table of LED of server blade7."
    ::= { blade7State 9 }

blade7StateLEDEntry    OBJECT-TYPE
    SYNTAX Blade7StateLEDEntry
    MAX-ACCESS not-accessible
    STATUS    current
    DESCRIPTION "This shows the entry of LED of server blade7."
    INDEX { blade7StateLEDIndex }
    ::= { blade7StateLEDTable 1 }

blade7StateLEDIndex    OBJECT-TYPE
    SYNTAX    Integer32
    MAX-ACCESS    read-only
    STATUS    current
    DESCRIPTION    "This shows the index of LED of server blade7."
    ::= { blade7StateLEDEntry 1 }

blade7StateLEDName    OBJECT-TYPE
    SYNTAX    DisplayString (SIZE(0..40))
    MAX-ACCESS    read-only
    STATUS    current
    DESCRIPTION    "This shows the name of LED of server blade7."
    ::= { blade7StateLEDEntry 2 }

blade7StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade7."
    ::= { blade7StateLEDEntry 3 }

blade7StateLEDColor    OBJECT-TYPE
    SYNTAX    INTEGER {
    blue (1),green (2),red (3),amber (4),unknown (5)
    }
    MAX-ACCESS    read-only
    STATUS    current
    DESCRIPTION    "This shows the color of LED of server blade7."
    ::= { blade7StateLEDEntry 4 }

Blade7StateLEDEntry ::= SEQUENCE {
    blade7StateLEDIndex
        Integer32,
    blade7StateLEDName
        DisplayString,
    blade7StateLEDState
        INTEGER,
    blade7StateLEDColor
        INTEGER
}

blade7StateOther    OBJECT IDENTIFIER ::= { blade7State 20 } 

blade7MaintMode    OBJECT-TYPE
    SYNTAX    INTEGER {
    Normal(1), CE-Maint-mode(2), User-Maint-mode(3), unknown(4)
    }
    MAX-ACCESS    read-only
    STATUS    current
    DESCRIPTION    "This shows the maintenance mode of server blade7."
    ::= { blade7StateOther 1 }

blade7Install    OBJECT IDENTIFIER ::= { blade7State 30 } 

blade7InsCPUSocketTable    OBJECT-TYPE
    SYNTAX SEQUENCE OF blade7InsCPUSocketEntry
    MAX-ACCESS not-accessible
    STATUS     current
    DESCRIPTION "This shows the table of CPU socket of server blade7."
    ::= { blade7Install 1 }

blade7InsCPUSocketEntry    OBJECT-TYPE
    SYNTAX Blade7InsCPUSocketEntry
    MAX-ACCESS not-accessible
    STATUS    current
    DESCRIPTION "This shows the entry of CPU socket of server blade7."
    INDEX { blade7InsCPUSocketIndex }
    ::= { blade7InsCPUSocketTable 1 }

blade7InsCPUSocketIndex    OBJECT-TYPE
    SYNTAX    Integer32
    MAX-ACCESS    read-only
    STATUS    current
    DESCRIPTION    "This shows the index of CPU socket of server blade7."
    ::= { blade7InsCPUSocketEntry 1 }

blade7InsCPUSocketNum    OBJECT-TYPE
    SYNTAX    Integer32
    MAX-ACCESS    read-only
    STATUS    current
    DESCRIPTION    "This shows the number of CPU sockets of server blade7."
    ::= { blade7InsCPUSocketEntry 2 }

blade7InsCPUSocketExist    OBJECT-TYPE
    SYNTAX    INTEGER {
    non-exist(1), exist(2), unknown(3)
    }
    MAX-ACCESS    read-only
    STATUS    current
    DESCRIPTION    "This shows the registrated state of CPU socket of server blade7."
    ::= { blade7InsCPUSocketEntry 3 }

blade7InsCPUSocketCPUName    OBJECT-TYPE
    SYNTAX    DisplayString (SIZE(0..40))
    MAX-ACCESS    read-only
    STATUS    current
    DESCRIPTION    "This shows the CPU name of CPU socket of server blade7."
    ::= { blade7InsCPUSocketEntry 4 }

blade7InsCPUSocketCPUFrequency    OBJECT-TYPE
    SYNTAX    Integer32
    UNITS    "MHz"
    MAX-ACCESS    read-only
    STATUS    current
    DESCRIPTION    "This shows the CPU frequency of CPU socket of server blade7."
    ::= { blade7InsCPUSocketEntry 5 }

blade7InsCPUSocketCPUStepping    OBJECT-TYPE
    SYNTAX    DisplayString 
    MAX-ACCESS    read-only
    STATUS    current
    DESCRIPTION    "This shows the CPU stepping of CPU socket of server blade7."
    ::= { blade7InsCPUSocketEntry 6 }

blade7InsCPUSocketCPUCoreNum    OBJECT-TYPE
    SYNTAX    Integer32
    MAX-ACCESS    read-only
    STATUS    current
    DESCRIPTION    "This shows the CPU core number of CPU socket of server blade7."
    ::= { blade7InsCPUSocketEntry 7 }

blade7InsCPUSocketCPUUpperLimitTemp    OBJECT-TYPE
    SYNTAX    Integer32
    UNITS    "0.1 degrees C"
    MAX-ACCESS    read-only
    STATUS    current
    DESCRIPTION    "This shows the maximum limited CPU temperature of server blade7."
    ::= { blade7InsCPUSocketEntry 8 }

blade7InsCPUSocketCPULowerLimitTemp    OBJECT-TYPE
    SYNTAX    Integer32
    UNITS    "0.1 degrees C"
    MAX-ACCESS    read-only
    STATUS    current
    DESCRIPTION    "This shows the minimum limited CPU temperature of server blade7."
    ::= { blade7InsCPUSocketEntry 9 }

blade7InsDIMMCapacity    OBJECT-TYPE
    SYNTAX    Integer32
    UNITS    "GB"
    MAX-ACCESS    read-only
    STATUS    current
    DESCRIPTION    "This shows the total amount of DIMM capacity of server blade7."
    ::= { blade7Install 2 }

Blade7InsCPUSocketEntry ::= SEQUENCE {
    blade7InsCPUSocketIndex
        Integer32,
    blade7InsCPUSocketNum
        Integer32,
    blade7InsCPUSocketExist
        INTEGER,
    blade7InsCPUSocketCPUName
        DisplayString,
    blade7InsCPUSocketCPUFrequency
        Integer32,
    blade7InsCPUSocketCPUStepping
        DisplayString,
    blade7InsCPUSocketCPUCoreNum
        Integer32,
    blade7InsCPUSocketCPUUpperLimitTemp
        Integer32,
    blade7InsCPUSocketCPULowerLimitTemp
        Integer32,
    blade7InsDIMMCapacity
        Integer32
}

blade7InsDIMMSlotTable    OBJECT-TYPE
    SYNTAX SEQUENCE OF blade7InsDIMMSlotEntry
    MAX-ACCESS not-accessible
    STATUS     current
    DESCRIPTION "This shows the table of DIMM slot of server blade7."
    ::= { blade7Install 3 }

blade7InsDIMMSlotEntry    OBJECT-TYPE
    SYNTAX Blade7InsDIMMSlotEntry
    MAX-ACCESS not-accessible
    STATUS    current
    DESCRIPTION "This shows the entry of DIMM slot of server blade7."
    INDEX { blade7InsDIMMSlotIndex }
    ::= { blade7InsDIMMSlotTable 1 }

blade7InsDIMMSlotIndex    OBJECT-TYPE
    SYNTAX    Integer32
    MAX-ACCESS    read-only
    STATUS    current
    DESCRIPTION    "This shows the index of DIMM slot of server blade7."
    ::= { blade7InsDIMMSlotEntry 1 }

blade7InsDIMMSlotExist    OBJECT-TYPE
    SYNTAX    INTEGER {
    non-exist(1), exist(2), unknown(3)
    }
    MAX-ACCESS    read-only
    STATUS    current
    DESCRIPTION    "This shows the registrated state of DIMM slot of server blade7."
    ::= { blade7InsDIMMSlotEntry 2 }

blade7InsDIMMSlotDIMMCapacity    OBJECT-TYPE
    SYNTAX    Integer32
    UNITS    "GB"
    MAX-ACCESS    read-only
    STATUS    current
    DESCRIPTION    "This shows the capacity of DIMM slots of server blade7."
    ::= { blade7InsDIMMSlotEntry 3 }

blade7InsDIMMSlotDIMMType    OBJECT-TYPE
    SYNTAX    DisplayString 
    MAX-ACCESS    read-only
    STATUS    current
    DESCRIPTION    "This shows the DIMM type of DIMM slot of server blade7."
    ::= { blade7InsDIMMSlotEntry 4 }

blade7InsDIMMSlotDIMMFrequency    OBJECT-TYPE
    SYNTAX    Integer32
    UNITS    "MHz"
    MAX-ACCESS    read-only
    STATUS    current
    DESCRIPTION    "This shows the DIMM frequency of DIMM slot of server blade7."
    ::= { blade7InsDIMMSlotEntry 5 }

blade7InsDIMMSlotDIMMCasLatency    OBJECT-TYPE
    SYNTAX    Integer32
    MAX-ACCESS    read-only
    STATUS    current
    DESCRIPTION    "This shows the DIMM cas latency of DIMM slot of server blade7."
    ::= { blade7InsDIMMSlotEntry 6 }

blade7InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade7."
    ::= { blade7InsDIMMSlotEntry 7 }

Blade7InsDIMMSlotEntry ::= SEQUENCE {
    blade7InsDIMMSlotIndex
        Integer32,
    blade7InsDIMMSlotExist
        INTEGER,
    blade7InsDIMMSlotDIMMCapacity
        Integer32,
    blade7InsDIMMSlotDIMMType
        DisplayString,
    blade7InsDIMMSlotDIMMFrequency
        Integer32,
    blade7InsDIMMSlotDIMMCasLatency
        Integer32,
    blade7InsDIMMSlotDIMMStatus
        INTEGER
}

blade7InsPCISlotTable    OBJECT-TYPE
    SYNTAX SEQUENCE OF blade7InsPCISlotEntry
    MAX-ACCESS not-accessible
    STATUS     current
    DESCRIPTION "This shows the table of PCI slot of server blade7."
    ::= { blade7Install 4 }

blade7InsPCISlotEntry    OBJECT-TYPE
    SYNTAX Blade7InsPCISlotEntry
    MAX-ACCESS not-accessible
    STATUS    current
    DESCRIPTION "This shows the entry of PCI slot of server blade7."
    INDEX { blade7InsPCISlotIndex }
    ::= { blade7InsPCISlotTable 1 }

blade7InsPCISlotIndex    OBJECT-TYPE
    SYNTAX    Integer32
    MAX-ACCESS    read-only
    STATUS    current
    DESCRIPTION    "This shows the index of PCI slot of server blade7."
    ::= { blade7InsPCISlotEntry 1 }

blade7InsPCISlotType    OBJECT-TYPE
    SYNTAX    DisplayString 
    MAX-ACCESS    read-only
    STATUS    current
    DESCRIPTION    "This shows the type of PCI slot of server blade7."
    ::= { blade7InsPCISlotEntry 2 }

blade7InsPCISlotExist    OBJECT-TYPE
    SYNTAX    INTEGER {
    non-exist(1), exist(2), unknown(3)
    }
    MAX-ACCESS    read-only
    STATUS    current
    DESCRIPTION    "This shows the registrated state of PCI slot of server blade7."
    ::= { blade7InsPCISlotEntry 3 }

blade7InsPCISlotPCIType    OBJECT-TYPE
    SYNTAX    DisplayString 
    MAX-ACCESS    read-only
    STATUS    current
    DESCRIPTION    "This shows the PCI type of PCI slot of server blade7."
    ::= { blade7InsPCISlotEntry 4 }

blade7InsPCISlotPCIProductName    OBJECT-TYPE
    SYNTAX    DisplayString 
    MAX-ACCESS    read-only
    STATUS    current
    DESCRIPTION    "This shows the PCI product name of PCI slot of server blade7."
    ::= { blade7InsPCISlotEntry 5 }

blade7InsPCISlotPCISerial    OBJECT-TYPE
    SYNTAX    DisplayString 
    MAX-ACCESS    read-only
    STATUS    current
    DESCRIPTION    "This shows the serial number of PCI slot of server blade7."
    ::= { blade7InsPCISlotEntry 6 }

blade7InsPCISlotPCIManufacturer    OBJECT-TYPE
    SYNTAX    DisplayString 
    MAX-ACCESS    read-only
    STATUS    current
    DESCRIPTION    "This shows the manufacturer of PCI slot of server blade7."
    ::= { blade7InsPCISlotEntry 7 }

blade7InsPCISlotNum    OBJECT-TYPE
    SYNTAX    Integer32
    MAX-ACCESS    read-only
    STATUS    current
    DESCRIPTION    "This shows the number of PCI slots of server blade7."
    ::= { blade7InsPCISlotEntry 8 }

Blade7InsPCISlotEntry ::= SEQUENCE {
    blade7InsPCISlotIndex
        Integer32,
    blade7InsPCISlotType
        DisplayString,
    blade7InsPCISlotExist
        INTEGER,
    blade7InsPCISlotPCIType
        DisplayString,
    blade7InsPCISlotPCIProductName
        DisplayString,
    blade7InsPCISlotPCISerial
        DisplayString,
    blade7InsPCISlotPCIManufacturer
        DisplayString,
    blade7InsPCISlotNum
        Integer32
}

blade7InsLOMTable    OBJECT-TYPE
    SYNTAX SEQUENCE OF blade7InsLOMEntry
    MAX-ACCESS not-accessible
    STATUS     current
    DESCRIPTION "This shows the table of onboard LAN of server blade7."
    ::= { blade7Install 5 }

blade7InsLOMEntry    OBJECT-TYPE
    SYNTAX Blade7InsLOMEntry
    MAX-ACCESS not-accessible
    STATUS    current
    DESCRIPTION "This shows the entry of onboard LAN of server blade7."
    INDEX { blade7InsLOMIndex }
    ::= { blade7InsLOMTable 1 }

blade7InsLOMIndex    OBJECT-TYPE
    SYNTAX    Integer32
    MAX-ACCESS    read-only
    STATUS    current
    DESCRIPTION    "This shows the index of onboard LAN of server blade7."
    ::= { blade7InsLOMEntry 1 }

blade7InsLOMType    OBJECT-TYPE
    SYNTAX    DisplayString 
    MAX-ACCESS    read-only
    STATUS    current
    DESCRIPTION    "This shows the type of onboard LAN of server blade7."
    ::= { blade7InsLOMEntry 2 }

blade7InsLOMLinkSpeed    OBJECT-TYPE
    SYNTAX    Integer32
    UNITS    "bps"
    MAX-ACCESS    read-only
    STATUS    current
    DESCRIPTION    "This shows the link speed of onboard LAN of server blade7."
    ::= { blade7InsLOMEntry 3 }

blade7InsLOMMAC    OBJECT-TYPE
    SYNTAX    DisplayString 
    MAX-ACCESS    read-only
    STATUS    current
    DESCRIPTION    "This shows the MAC address of onboard LAN of server blade7."
    ::= { blade7InsLOMEntry 4 }

blade7InsLOMLinkStatus    OBJECT-TYPE
    SYNTAX    INTEGER {
    up (1),down (2),unknown (3)
    }
    MAX-ACCESS    read-only
    STATUS    current
    DESCRIPTION    "This shows the link state of onboard LAN of server blade7."
    ::= { blade7InsLOMEntry 5 }

blade7InsLOMPortDivide    OBJECT-TYPE
    SYNTAX    INTEGER {
    possible (1),Impossible (2),unknown (3)
    }
    MAX-ACCESS    read-only
    STATUS    current
    DESCRIPTION    "This shows the port divide propriety of onboard LAN of server blade7."
    ::= { blade7InsLOMEntry 6 }

blade7InsLOMPortDivideNum    OBJECT-TYPE
    SYNTAX    Integer32
    MAX-ACCESS    read-only
    STATUS    current
    DESCRIPTION    "This shows the port divide number of onboard LAN of server blade7."
    ::= { blade7InsLOMEntry 7 }

Blade7InsLOMEntry ::= SEQUENCE {
    blade7InsLOMIndex
        Integer32,
    blade7InsLOMType
        DisplayString,
    blade7InsLOMLinkSpeed
        Integer32,
    blade7InsLOMMAC
        DisplayString,
    blade7InsLOMLinkStatus
        INTEGER,
    blade7InsLOMPortDivide
        INTEGER,
    blade7InsLOMPortDivideNum
        Integer32
}

blade7HDDSlotTable    OBJECT-TYPE
    SYNTAX SEQUENCE OF blade7HDDSlotEntry
    MAX-ACCESS not-accessible
    STATUS     current
    DESCRIPTION "This shows the table of HDD slot of server blade7."
    ::= { blade7Install 7 }

blade7HDDSlotEntry    OBJECT-TYPE
    SYNTAX Blade7HDDSlotEntry
    MAX-ACCESS not-accessible
    STATUS    current
    DESCRIPTION "This shows the entry of HDD slot of server blade7."
    INDEX { blade7HDDSlotIndex }
    ::= { blade7HDDSlotTable 1 }

blade7HDDSlotIndex    OBJECT-TYPE
    SYNTAX    Integer32
    MAX-ACCESS    read-only
    STATUS    current
    DESCRIPTION    "This shows the index of HDD slot of server blade7."
    ::= { blade7HDDSlotEntry 1 }

blade7HDDSlotNum    OBJECT-TYPE
    SYNTAX    Integer32
    MAX-ACCESS    read-only
    STATUS    current
    DESCRIPTION    "This shows the number of HDD slots of server blade7."
    ::= { blade7HDDSlotEntry 2 }

blade7HDDSlotExist    OBJECT-TYPE
    SYNTAX    INTEGER {
    non-exist(1), exist(2), unknown(3)
    }
    MAX-ACCESS    read-only
    STATUS    current
    DESCRIPTION    "This shows the registrated state of HDD slot of server blade7."
    ::= { blade7HDDSlotEntry 3 }

blade7HDDSlotHDDType    OBJECT-TYPE
    SYNTAX    DisplayString 
    MAX-ACCESS    read-only
    STATUS    current
    DESCRIPTION    "This shows the HDD type of HDD slot of server blade7."
    ::= { blade7HDDSlotEntry 4 }

blade7HDDSlotHDDProductName    OBJECT-TYPE
    SYNTAX    DisplayString 
    MAX-ACCESS    read-only
    STATUS    current
    DESCRIPTION    "This shows the HDD product name of HDD slot of server blade7."
    ::= { blade7HDDSlotEntry 5 }

blade7HDDSlotHDDModel    OBJECT-TYPE
    SYNTAX    DisplayString 
    MAX-ACCESS    read-only
    STATUS    current
    DESCRIPTION    "This shows the HDD model of HDD slot of server blade7."
    ::= { blade7HDDSlotEntry 6 }

blade7HDDSlotHDDSerialNum    OBJECT-TYPE
    SYNTAX    DisplayString 
    MAX-ACCESS    read-only
    STATUS    current
    DESCRIPTION    "This shows the HDD serial number of HDD slot of server blade7."
    ::= { blade7HDDSlotEntry 7 }

blade7HDDSlotHDDCapacity    OBJECT-TYPE
    SYNTAX    Integer32
    UNITS    "GB"
    MAX-ACCESS    read-only
    STATUS    current
    DESCRIPTION    "This shows the HDD capacity of HDD slots of server blade7."
    ::= { blade7HDDSlotEntry 8 }

blade7HDDSlotHDDRPM    OBJECT-TYPE
    SYNTAX    Integer32
    UNITS    "rpm"
    MAX-ACCESS    read-only
    STATUS    current
    DESCRIPTION    "This shows the HDD drive speed of HDD slot of server blade7."
    ::= { blade7HDDSlotEntry 9 }

blade7HDDSlotHDDStatePower    OBJECT-TYPE
    SYNTAX    INTEGER {
    poweroff (1), poweron (2), unknown (3)
    }
    MAX-ACCESS    read-only
    STATUS    current
    DESCRIPTION    "This shows the HDD power supply state of HDD slot of server blade7."
    ::= { blade7HDDSlotEntry 10 }

blade7HDDSlotHDDStateHealth    OBJECT-TYPE
    SYNTAX    INTEGER {
    normal (1),fail (2),unknown (3),rebuild (4)
    }
    MAX-ACCESS    read-only
    STATUS    current
    DESCRIPTION    "This shows the HDD health state of HDD slot of server blade7."
    ::= { blade7HDDSlotEntry 11 }

blade7HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade7(activity)."
    ::= { blade7HDDSlotEntry 12 }

blade7HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade7(status)."
    ::= { blade7HDDSlotEntry 13 }

blade7HDDSlotHDDFWInfoName    OBJECT-TYPE
    SYNTAX    DisplayString 
    MAX-ACCESS    read-only
    STATUS    current
    DESCRIPTION    "This shows the HDD firmware name of HDD slot of server blade7."
    ::= { blade7HDDSlotEntry 20 }

blade7HDDSlotHDDFWInfoCurrentVer    OBJECT-TYPE
    SYNTAX    DisplayString 
    MAX-ACCESS    read-only
    STATUS    current
    DESCRIPTION    "This shows the HDD firmware current version of HDD slot of server blade7."
    ::= { blade7HDDSlotEntry 21 }

blade7HDDSlotHDDFWInfoNextVer    OBJECT-TYPE
    SYNTAX    DisplayString 
    MAX-ACCESS    read-only
    STATUS    current
    DESCRIPTION    "This shows the HDD firmware next version of HDD slot of server blade7."
    ::= { blade7HDDSlotEntry 22 }

Blade7HDDSlotEntry ::= SEQUENCE {
    blade7HDDSlotIndex
        Integer32,
    blade7HDDSlotNum
        Integer32,
    blade7HDDSlotExist
        INTEGER,
    blade7HDDSlotHDDType
        DisplayString,
    blade7HDDSlotHDDProductName
        DisplayString,
    blade7HDDSlotHDDModel
        DisplayString,
    blade7HDDSlotHDDSerialNum
        DisplayString,
    blade7HDDSlotHDDCapacity
        Integer32,
    blade7HDDSlotHDDRPM
        Integer32,
    blade7HDDSlotHDDStatePower
        INTEGER,
    blade7HDDSlotHDDStateHealth
        INTEGER,
    blade7HDDSlotHDDStateLEDACT
        INTEGER,
    blade7HDDSlotHDDStateLEDSTS
        INTEGER,
    blade7HDDSlotHDDFWInfoName
        DisplayString,
    blade7HDDSlotHDDFWInfoCurrentVer
        DisplayString,
    blade7HDDSlotHDDFWInfoNextVer
        DisplayString
}

blade7ExpansionHDDSlotTable    OBJECT-TYPE
    SYNTAX SEQUENCE OF blade7ExpansionHDDSlotEntry
    MAX-ACCESS not-accessible
    STATUS     current
    DESCRIPTION "This shows the table of expansion HDD slot of server blade7."
    ::= { blade7Install 8 }

blade7ExpansionHDDSlotEntry    OBJECT-TYPE
    SYNTAX Blade7ExpansionHDDSlotEntry
    MAX-ACCESS not-accessible
    STATUS    current
    DESCRIPTION "This shows the entry of expansion HDD slot of server blade7."
    INDEX { blade7ExpansionHDDSlotIndex }
    ::= { blade7ExpansionHDDSlotTable 1 }

blade7ExpansionHDDSlotIndex    OBJECT-TYPE
    SYNTAX    Integer32
    MAX-ACCESS    read-only
    STATUS    current
    DESCRIPTION    "This shows the index of expansion HDD slot of server blade7."
    ::= { blade7ExpansionHDDSlotEntry 1 }

blade7ExpansionHDDSlotNum    OBJECT-TYPE
    SYNTAX    Integer32
    MAX-ACCESS    read-only
    STATUS    current
    DESCRIPTION    "This shows the number of expansion HDD slots of server blade7."
    ::= { blade7ExpansionHDDSlotEntry 2 }

blade7ExpansionHDDSlotExist    OBJECT-TYPE
    SYNTAX    INTEGER {
    non-exist(1), exist(2), unknown(3)
    }
    MAX-ACCESS    read-only
    STATUS    current
    DESCRIPTION    "This shows the registrated state of expansion HDD slot of server blade7."
    ::= { blade7ExpansionHDDSlotEntry 3 }

blade7ExpansionHDDSlotHDDType    OBJECT-TYPE
    SYNTAX    DisplayString 
    MAX-ACCESS    read-only
    STATUS    current
    DESCRIPTION    "This shows the HDD type of expansion HDD slot of server blade7."
    ::= { blade7ExpansionHDDSlotEntry 4 }

blade7ExpansionHDDSlotHDDProductName    OBJECT-TYPE
    SYNTAX    DisplayString 
    MAX-ACCESS    read-only
    STATUS    current
    DESCRIPTION    "This shows the HDD product name of expansion HDD slot of server blade7."
    ::= { blade7ExpansionHDDSlotEntry 5 }

blade7ExpansionHDDSlotHDDModel    OBJECT-TYPE
    SYNTAX    DisplayString 
    MAX-ACCESS    read-only
    STATUS    current
    DESCRIPTION    "This shows the HDD model of expansion HDD slot of server blade7."
    ::= { blade7ExpansionHDDSlotEntry 6 }

blade7ExpansionHDDSlotHDDSerialNum    OBJECT-TYPE
    SYNTAX    DisplayString 
    MAX-ACCESS    read-only
    STATUS    current
    DESCRIPTION    "This shows the HDD serial number of expansion HDD slot of server blade7."
    ::= { blade7ExpansionHDDSlotEntry 7 }

blade7ExpansionHDDSlotHDDCapacity    OBJECT-TYPE
    SYNTAX    Integer32
    UNITS    "GB"
    MAX-ACCESS    read-only
    STATUS    current
    DESCRIPTION    "This shows the HDD capacity of expansion HDD slots of server blade7."
    ::= { blade7ExpansionHDDSlotEntry 8 }

blade7ExpansionHDDSlotHDDRPM    OBJECT-TYPE
    SYNTAX    Integer32
    UNITS    "rpm"
    MAX-ACCESS    read-only
    STATUS    current
    DESCRIPTION    "This shows the HDD drive speed of expansion HDD slot of server blade7."
    ::= { blade7ExpansionHDDSlotEntry 9 }

blade7ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade7."
    ::= { blade7ExpansionHDDSlotEntry 10 }

blade7ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade7."
    ::= { blade7ExpansionHDDSlotEntry 11 }

blade7ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade7(activity)."
    ::= { blade7ExpansionHDDSlotEntry 12 }

blade7ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade7(status)."
    ::= { blade7ExpansionHDDSlotEntry 13 }

blade7ExpansionHDDSlotHDDFWInfoName    OBJECT-TYPE
    SYNTAX    DisplayString 
    MAX-ACCESS    read-only
    STATUS    current
    DESCRIPTION    "This shows the HDD firmware name of expansion HDD slot of server blade7."
    ::= { blade7ExpansionHDDSlotEntry 20 }

blade7ExpansionHDDSlotHDDFWInfoCurrentVer    OBJECT-TYPE
    SYNTAX    DisplayString 
    MAX-ACCESS    read-only
    STATUS    current
    DESCRIPTION    "This shows the HDD firmware current version of expansion HDD slot of server blade7."
    ::= { blade7ExpansionHDDSlotEntry 21 }

blade7ExpansionHDDSlotHDDFWInfoNextVer    OBJECT-TYPE
    SYNTAX    DisplayString 
    MAX-ACCESS    read-only
    STATUS    current
    DESCRIPTION    "This shows the HDD firmware next version of expansion HDD slot of server blade7."
    ::= { blade7ExpansionHDDSlotEntry 22 }

Blade7ExpansionHDDSlotEntry ::= SEQUENCE {
    blade7ExpansionHDDSlotIndex
        Integer32,
    blade7ExpansionHDDSlotNum
        Integer32,
    blade7ExpansionHDDSlotExist
        INTEGER,
    blade7ExpansionHDDSlotHDDType
        DisplayString,
    blade7ExpansionHDDSlotHDDProductName
        DisplayString,
    blade7ExpansionHDDSlotHDDModel
        DisplayString,
    blade7ExpansionHDDSlotHDDSerialNum
        DisplayString,
    blade7ExpansionHDDSlotHDDCapacity
        Integer32,
    blade7ExpansionHDDSlotHDDRPM
        Integer32,
    blade7ExpansionHDDSlotHDDStatePower
        INTEGER,
    blade7ExpansionHDDSlotHDDStateHealth
        INTEGER,
    blade7ExpansionHDDSlotHDDStateLEDACT
        INTEGER,
    blade7ExpansionHDDSlotHDDStateLEDSTS
        INTEGER,
    blade7ExpansionHDDSlotHDDFWInfoName
        DisplayString,
    blade7ExpansionHDDSlotHDDFWInfoCurrentVer
        DisplayString,
    blade7ExpansionHDDSlotHDDFWInfoNextVer
        DisplayString
}

blade7VoltageSensorTable    OBJECT-TYPE
    SYNTAX SEQUENCE OF blade7VoltageSensorEntry
    MAX-ACCESS not-accessible
    STATUS     current
    DESCRIPTION "This shows the table of voltage sensor of server blade7."
    ::= { blade7State 40 }

blade7VoltageSensorEntry    OBJECT-TYPE
    SYNTAX Blade7VoltageSensorEntry
    MAX-ACCESS not-accessible
    STATUS    current
    DESCRIPTION "This shows the entry of voltage sensor of server blade7."
    INDEX { blade7VoltageSensorIndex }
    ::= { blade7VoltageSensorTable 1 }

blade7VoltageSensorIndex    OBJECT-TYPE
    SYNTAX    Integer32
    MAX-ACCESS    read-only
    STATUS    current
    DESCRIPTION    "This shows the index of voltage sensor of server blade7."
    ::= { blade7VoltageSensorEntry 1 }

blade7VoltageSensorName    OBJECT-TYPE
    SYNTAX    DisplayString 
    MAX-ACCESS    read-only
    STATUS    current
    DESCRIPTION    "This shows the voltage sensor name of server blade7."
    ::= { blade7VoltageSensorEntry 2 }

blade7VoltageSensorValue    OBJECT-TYPE
    SYNTAX    Integer32
    UNITS    "0.1 V"
    MAX-ACCESS    read-only
    STATUS    current
    DESCRIPTION    "This shows the voltage sensor value of server blade7."
    ::= { blade7VoltageSensorEntry 3 }

blade7VoltageSensorValid    OBJECT-TYPE
    SYNTAX    INTEGER {
    invalid (1),valid (2),unknown (3)
    }
    MAX-ACCESS    read-only
    STATUS    current
    DESCRIPTION    "This shows the validity of voltage sensor value of server blade7."
    ::= { blade7VoltageSensorEntry 4 }

Blade7VoltageSensorEntry ::= SEQUENCE {
    blade7VoltageSensorIndex
        Integer32,
    blade7VoltageSensorName
        DisplayString,
    blade7VoltageSensorValue
        Integer32,
    blade7VoltageSensorValid
        INTEGER
}

blade7TempSensorTable    OBJECT-TYPE
    SYNTAX SEQUENCE OF blade7TempSensorEntry
    MAX-ACCESS not-accessible
    STATUS     current
    DESCRIPTION "This shows the table of temperature sensor of server blade7."
    ::= { blade7State 41 }

blade7TempSensorEntry    OBJECT-TYPE
    SYNTAX Blade7TempSensorEntry
    MAX-ACCESS not-accessible
    STATUS    current
    DESCRIPTION "This shows the entry of temperature sensor of server blade7."
    INDEX { blade7TempSensorIndex }
    ::= { blade7TempSensorTable 1 }

blade7TempSensorIndex    OBJECT-TYPE
    SYNTAX    Integer32
    MAX-ACCESS    read-only
    STATUS    current
    DESCRIPTION    "This shows the index of temperature sensor of server blade7."
    ::= { blade7TempSensorEntry 1 }

blade7TempSensorName    OBJECT-TYPE
    SYNTAX    DisplayString 
    MAX-ACCESS    read-only
    STATUS    current
    DESCRIPTION    "This shows the temperature sensor name of server blade7."
    ::= { blade7TempSensorEntry 2 }

blade7TempSensorValue    OBJECT-TYPE
    SYNTAX    Integer32
    UNITS    "0.1 degrees C"
    MAX-ACCESS    read-only
    STATUS    current
    DESCRIPTION    "This shows the temperature sensor value of server blade7."
    ::= { blade7TempSensorEntry 3 }

blade7TempSensorValid    OBJECT-TYPE
    SYNTAX    INTEGER {
    invalid (1),valid (2),unknown (3)
    }
    MAX-ACCESS    read-only
    STATUS    current
    DESCRIPTION    "This shows the validity of temperature sensor value of server blade7."
    ::= { blade7TempSensorEntry 4 }

Blade7TempSensorEntry ::= SEQUENCE {
    blade7TempSensorIndex
        Integer32,
    blade7TempSensorName
        DisplayString,
    blade7TempSensorValue
        Integer32,
    blade7TempSensorValid
        INTEGER
}

blade7FWInfo    OBJECT IDENTIFIER ::= { blade7 5 } 

blade7FWInfoTotalCurrentVer    OBJECT-TYPE
    SYNTAX    DisplayString (SIZE(0..40))
    MAX-ACCESS    read-only
    STATUS    current
    DESCRIPTION    "This shows the total current version of firmware of server blade7."
    ::= { blade7FWInfo 1 }

blade7FWInfoTotalNextVer    OBJECT-TYPE
    SYNTAX    DisplayString (SIZE(0..40))
    MAX-ACCESS    read-only
    STATUS    current
    DESCRIPTION    "This shows the total next version of firmware of server blade7."
    ::= { blade7FWInfo 2 }

blade7FWInfoTable    OBJECT-TYPE
    SYNTAX SEQUENCE OF blade7FWInfoEntry
    MAX-ACCESS not-accessible
    STATUS     current
    DESCRIPTION "This shows the table of firmware information of server blade7."
    ::= { blade7FWInfo 3 }

blade7FWInfoEntry    OBJECT-TYPE
    SYNTAX Blade7FWInfoEntry
    MAX-ACCESS not-accessible
    STATUS    current
    DESCRIPTION "This shows the entry of firmware information of server blade7."
    INDEX { blade7FWInfoIndex }
    ::= { blade7FWInfoTable 1 }

blade7FWInfoIndex    OBJECT-TYPE
    SYNTAX    Integer32
    MAX-ACCESS    read-only
    STATUS    current
    DESCRIPTION    "This shows the index of firmware information of server blade7."
    ::= { blade7FWInfoEntry 1 }

blade7FWInfoName    OBJECT-TYPE
    SYNTAX    DisplayString (SIZE(0..40))
    MAX-ACCESS    read-only
    STATUS    current
    DESCRIPTION    "This shows the firmware name of server blade7."
    ::= { blade7FWInfoEntry 2 }

blade7FWCurrentVer    OBJECT-TYPE
    SYNTAX    DisplayString (SIZE(0..40))
    MAX-ACCESS    read-only
    STATUS    current
    DESCRIPTION    "This shows the firmware current version of server blade7."
    ::= { blade7FWInfoEntry 3 }

blade7FWInfoNextVer    OBJECT-TYPE
    SYNTAX    DisplayString (SIZE(0..40))
    MAX-ACCESS    read-only
    STATUS    current
    DESCRIPTION    "This shows the firmware next version of server blade7."
    ::= { blade7FWInfoEntry 4 }

blade7FWInfoHVMCurrentVer    OBJECT-TYPE
    SYNTAX    DisplayString (SIZE(0..40))
    MAX-ACCESS    read-only
    STATUS    current
    DESCRIPTION    "This shows the HVM current version of server blade7."
    ::= { blade7FWInfo 4 }

blade7FWInfoHVMNextVer    OBJECT-TYPE
    SYNTAX    DisplayString (SIZE(0..40))
    MAX-ACCESS    read-only
    STATUS    current
    DESCRIPTION    "This shows the HVM next version of server blade7."
    ::= { blade7FWInfo 5 }

Blade7FWInfoEntry ::= SEQUENCE {
    blade7FWInfoIndex
        Integer32,
    blade7FWInfoName
        DisplayString,
    blade7FWCurrentVer
        DisplayString,
    blade7FWInfoNextVer
        DisplayString,
    blade7FWInfoHVMCurrentVer
        DisplayString,
    blade7FWInfoHVMNextVer
        DisplayString
}

blade8    OBJECT IDENTIFIER ::= { blade 8 } 

blade8BasicInfo    OBJECT IDENTIFIER ::= { blade8 1 } 

blade8InfoProductName    OBJECT-TYPE
    SYNTAX    DisplayString (SIZE(0..40))
    MAX-ACCESS    read-only
    STATUS    current
    DESCRIPTION    "This shows the product name of server blade8."
    ::= { blade8BasicInfo 1 }

blade8InfoModel    OBJECT-TYPE
    SYNTAX    DisplayString (SIZE(0..40))
    MAX-ACCESS    read-only
    STATUS    current
    DESCRIPTION    "This shows the model name of server blade8."
    ::= { blade8BasicInfo 2 }

blade8InfoSerialNum    OBJECT-TYPE
    SYNTAX    DisplayString (SIZE(0..40))
    MAX-ACCESS    read-only
    STATUS    current
    DESCRIPTION    "This shows the serial number of server blade8."
    ::= { blade8BasicInfo 3 }

blade8InfoProductVersion    OBJECT-TYPE
    SYNTAX    DisplayString (SIZE(0..40))
    MAX-ACCESS    read-only
    STATUS    current
    DESCRIPTION    "This shows the product version of server blade8."
    ::= { blade8BasicInfo 4 }

blade8InfoProductManufacturer    OBJECT-TYPE
    SYNTAX    DisplayString (SIZE(0..40))
    MAX-ACCESS    read-only
    STATUS    current
    DESCRIPTION    "This shows the product manufacturer of server blade8."
    ::= { blade8BasicInfo 5 }

blade8InfoBoardProductName    OBJECT-TYPE
    SYNTAX    DisplayString (SIZE(0..40))
    MAX-ACCESS    read-only
    STATUS    current
    DESCRIPTION    "This shows the board product name of server blade8."
    ::= { blade8BasicInfo 7 }

blade8InfoBoardSerialNum    OBJECT-TYPE
    SYNTAX    DisplayString (SIZE(0..40))
    MAX-ACCESS    read-only
    STATUS    current
    DESCRIPTION    "This shows the board serial number of server blade8."
    ::= { blade8BasicInfo 8 }

blade8InfoBoardManufacturer    OBJECT-TYPE
    SYNTAX    DisplayString (SIZE(0..40))
    MAX-ACCESS    read-only
    STATUS    current
    DESCRIPTION    "This shows the board manufacturer of server blade8."
    ::= { blade8BasicInfo 9 }

blade8InfoUUID    OBJECT-TYPE
    SYNTAX    DisplayString (SIZE(0..40))
    MAX-ACCESS    read-only
    STATUS    current
    DESCRIPTION    "This shows UUID(universal Unique ID) of server blade8."
    ::= { blade8BasicInfo 10 }

blade8InfoLogicalPartitionSupport    OBJECT-TYPE
    SYNTAX    INTEGER {
    not-support(1), support(2),unknown(3)
    }
    MAX-ACCESS    read-only
    STATUS    current
    DESCRIPTION    "This shows whether the server blade8 supports HVM or not of server blade1."
    ::= { blade8BasicInfo 11 }

blade8InfoRemoteKVMSupport    OBJECT-TYPE
    SYNTAX    INTEGER {
    not-support(1), support(2),unknown(3)
    }
    MAX-ACCESS    read-only
    STATUS    current
    DESCRIPTION    "This shows whether the server blade8 supports remote KVM or not of server blade1."
    ::= { blade8BasicInfo 12 }

blade8InfoSpec    OBJECT IDENTIFIER ::= { blade8BasicInfo 20 } 

blade8SpecInputCurrentType    OBJECT-TYPE
    SYNTAX    INTEGER {
    ac(1),dc(2),unknown(3)
    }
    MAX-ACCESS    read-only
    STATUS    current
    DESCRIPTION    "This shows the currency type of server blade8."
    ::= { blade8InfoSpec 1 }

blade8SpecRateVoltage    OBJECT-TYPE
    SYNTAX    Integer32
    UNITS    "0.1 V"
    MAX-ACCESS    read-only
    STATUS    current
    DESCRIPTION    "This shows the rated voltage of server blade8."
    ::= { blade8InfoSpec 2 }

blade8SpecConsumptionCurrent    OBJECT-TYPE
    SYNTAX    Integer32
    UNITS    "0.1 A"
    MAX-ACCESS    read-only
    STATUS    current
    DESCRIPTION    "This shows the consumption current of server blade8."
    ::= { blade8InfoSpec 3 }

blade8SpecPowerConsumption    OBJECT-TYPE
    SYNTAX    Integer32
    UNITS    "W"
    MAX-ACCESS    read-only
    STATUS    current
    DESCRIPTION    "This shows the power consumption of server blade8."
    ::= { blade8InfoSpec 4 }

blade8SpecMass    OBJECT-TYPE
    SYNTAX    Integer32
    UNITS    "0.1 kg"
    MAX-ACCESS    read-only
    STATUS    current
    DESCRIPTION    "This shows the weight of server blade8."
    ::= { blade8InfoSpec 5 }

blade8InfoUpperLimitIntakeTemp    OBJECT-TYPE
    SYNTAX    Integer32
    UNITS    "0.1 degrees C"
    MAX-ACCESS    read-only
    STATUS    current
    DESCRIPTION    "This shows the maximum limited intake temperature of server blade8."
    ::= { blade8InfoSpec 6 }

blade8InfoLowerLimitIntakeTemp    OBJECT-TYPE
    SYNTAX    Integer32
    UNITS    "0.1 degrees C"
    MAX-ACCESS    read-only
    STATUS    current
    DESCRIPTION    "This shows the minimum limited intake temperature of server blade8."
    ::= { blade8InfoSpec 7 }

blade8SpecSize    OBJECT-TYPE
    SYNTAX    DisplayString (SIZE(0..40))
    MAX-ACCESS    read-only
    STATUS    current
    DESCRIPTION    "This shows the size of server blade8."
    ::= { blade8InfoSpec 8 }

blade8SpecOccupySlots    OBJECT-TYPE
    SYNTAX    Integer32
    MAX-ACCESS    read-only
    STATUS    current
    DESCRIPTION    "This shows the dedicated number of slots of server blade8."
    ::= { blade8InfoSpec 9 }

blade8SpecExpansionBladeSlot    OBJECT-TYPE
    SYNTAX    Integer32
    MAX-ACCESS    read-only
    STATUS    current
    DESCRIPTION    "This shows the number of slots of expansion blade of server blade8."
    ::= { blade8InfoSpec 10 }

blade8InfoExpansionBladeTable    OBJECT-TYPE
    SYNTAX SEQUENCE OF blade8InfoExpansionBladeEntry
    MAX-ACCESS not-accessible
    STATUS     current
    DESCRIPTION "This shows the table of expansion blade slot of server blade8."
    ::= { blade8BasicInfo 30 }

blade8InfoExpansionBladeEntry    OBJECT-TYPE
    SYNTAX Blade8InfoExpansionBladeEntry
    MAX-ACCESS not-accessible
    STATUS    current
    DESCRIPTION "This shows the entry of expansion blade slot of server blade8."
    INDEX { blade8InfoExpansionBladeIndex }
    ::= { blade8InfoExpansionBladeTable 1 }

blade8InfoExpansionBladeIndex    OBJECT-TYPE
    SYNTAX    Integer32
    MAX-ACCESS    read-only
    STATUS    current
    DESCRIPTION    "This shows the index of expansion blade slot of server blade8."
    ::= { blade8InfoExpansionBladeEntry 1 }

blade8InfoExpansionBladeExist    OBJECT-TYPE
    SYNTAX    INTEGER {
    non-exist(1), exist(2), unknown(3)
    }
    MAX-ACCESS    read-only
    STATUS    current
    DESCRIPTION    "This shows the registrated state of expansion blade of server blade8."
    ::= { blade8InfoExpansionBladeEntry 2 }

blade8InfoExpansionBladeProductName    OBJECT-TYPE
    SYNTAX    DisplayString (SIZE(0..40))
    MAX-ACCESS    read-only
    STATUS    current
    DESCRIPTION    "This shows the product name of expansion blade of server blade8."
    ::= { blade8InfoExpansionBladeEntry 3 }

blade8InfoExpansionBladeModel    OBJECT-TYPE
    SYNTAX    DisplayString (SIZE(0..40))
    MAX-ACCESS    read-only
    STATUS    current
    DESCRIPTION    "This shows the model name of expansion blade of server blade8."
    ::= { blade8InfoExpansionBladeEntry 4 }

blade8InfoExpansionBladeSerialNum    OBJECT-TYPE
    SYNTAX    DisplayString (SIZE(0..40))
    MAX-ACCESS    read-only
    STATUS    current
    DESCRIPTION    "This shows the serial number of expansion blade of server blade8."
    ::= { blade8InfoExpansionBladeEntry 5 }

blade8InfoExpansionBladeProductVersion    OBJECT-TYPE
    SYNTAX    DisplayString (SIZE(0..40))
    MAX-ACCESS    read-only
    STATUS    current
    DESCRIPTION    "This shows the product version of expansion blade of server blade8."
    ::= { blade8InfoExpansionBladeEntry 6 }

blade8InfoExpansionBladeProductManufacturer    OBJECT-TYPE
    SYNTAX    DisplayString (SIZE(0..40))
    MAX-ACCESS    read-only
    STATUS    current
    DESCRIPTION    "This shows the product manufacturer of expansion blade of server blade8."
    ::= { blade8InfoExpansionBladeEntry 7 }

blade8InfoExpansionBladeBoardProductName    OBJECT-TYPE
    SYNTAX    DisplayString (SIZE(0..40))
    MAX-ACCESS    read-only
    STATUS    current
    DESCRIPTION    "This shows the board product name of expansion blade of server blade8."
    ::= { blade8InfoExpansionBladeEntry 9 }

blade8InfoExpansionBladeBoardSerialNum    OBJECT-TYPE
    SYNTAX    DisplayString (SIZE(0..40))
    MAX-ACCESS    read-only
    STATUS    current
    DESCRIPTION    "This shows the board serial number of expansion blade of server blade8."
    ::= { blade8InfoExpansionBladeEntry 10 }

blade8InfoExpansionBladeBoardManufacturer    OBJECT-TYPE
    SYNTAX    DisplayString (SIZE(0..40))
    MAX-ACCESS    read-only
    STATUS    current
    DESCRIPTION    "This shows the board manufacturer of expansion blade of server blade8."
    ::= { blade8InfoExpansionBladeEntry 11 }

Blade8InfoExpansionBladeEntry ::= SEQUENCE {
    blade8InfoExpansionBladeIndex
        Integer32,
    blade8InfoExpansionBladeExist
        INTEGER,
    blade8InfoExpansionBladeProductName
        DisplayString,
    blade8InfoExpansionBladeModel
        DisplayString,
    blade8InfoExpansionBladeSerialNum
        DisplayString,
    blade8InfoExpansionBladeProductVersion
        DisplayString,
    blade8InfoExpansionBladeProductManufacturer
        DisplayString,
    blade8InfoExpansionBladeBoardProductName
        DisplayString,
    blade8InfoExpansionBladeBoardSerialNum
        DisplayString,
    blade8InfoExpansionBladeBoardManufacturer
        DisplayString
}

blade8Capacity    OBJECT IDENTIFIER ::= { blade8 2 } 

blade8CapacityCPUSocket    OBJECT-TYPE
    SYNTAX    Integer32
    MAX-ACCESS    read-only
    STATUS    current
    DESCRIPTION    "This shows the capacity of CPU sockets of server blade8."
    ::= { blade8Capacity 1 }

blade8CapacityDIMMSlot    OBJECT-TYPE
    SYNTAX    Integer32
    MAX-ACCESS    read-only
    STATUS    current
    DESCRIPTION    "This shows the capacity of DIMM slots of server blade8."
    ::= { blade8Capacity 2 }

blade8CapacityPCISlot    OBJECT-TYPE
    SYNTAX    Integer32
    MAX-ACCESS    read-only
    STATUS    current
    DESCRIPTION    "This shows the capacity of PCI slots of server blade8."
    ::= { blade8Capacity 3 }

blade8CapacityLOM    OBJECT-TYPE
    SYNTAX    Integer32
    MAX-ACCESS    read-only
    STATUS    current
    DESCRIPTION    "This shows the capacity of onboard LAN ports of server blade8."
    ::= { blade8Capacity 4 }

blade8CapacityFan    OBJECT-TYPE
    SYNTAX    Integer32
    MAX-ACCESS    read-only
    STATUS    current
    DESCRIPTION    "This shows the capacity of onboard fans of server blade8."
    ::= { blade8Capacity 5 }

blade8CapacityHDDSlot    OBJECT-TYPE
    SYNTAX    Integer32
    MAX-ACCESS    read-only
    STATUS    current
    DESCRIPTION    "This shows the capacity of HDD slots of server blade8."
    ::= { blade8Capacity 6 }

blade8CapacityVoltageSensor    OBJECT-TYPE
    SYNTAX    Integer32
    MAX-ACCESS    read-only
    STATUS    current
    DESCRIPTION    "This shows the capacity of voltage sensors of blade8."
    ::= { blade8Capacity 7 }

blade8CapacityTempSensor    OBJECT-TYPE
    SYNTAX    Integer32
    MAX-ACCESS    read-only
    STATUS    current
    DESCRIPTION    "This shows the capacity of temperature sensors of blade8."
    ::= { blade8Capacity 8 }

blade8CapacityExpansionHDDSlot    OBJECT-TYPE
    SYNTAX    Integer32
    MAX-ACCESS    read-only
    STATUS    current
    DESCRIPTION    "This shows the capacity of expansion HDD slots of server blade8."
    ::= { blade8Capacity 9 }

blade8CapacityLED    OBJECT-TYPE
    SYNTAX    Integer32
    MAX-ACCESS    read-only
    STATUS    current
    DESCRIPTION    "This shows the capacity of count of LEDs of server blade8."
    ::= { blade8Capacity 10 }

blade8Settings    OBJECT IDENTIFIER ::= { blade8 3 } 

blade8SettingsBelongPartitionNum    OBJECT-TYPE
    SYNTAX    Integer32
    MAX-ACCESS    read-only
    STATUS    current
    DESCRIPTION    "This shows the partition number of server blade8."
    ::= { blade8Settings 1 }

blade8SettingsDetailHVMLicenceModel    OBJECT-TYPE
    SYNTAX    DisplayString (SIZE(0..40))
    MAX-ACCESS    read-only
    STATUS    current
    DESCRIPTION    "This shows the HVM licence of detailed server blade8 (model). "
    ::= { blade8Settings 2 }

blade8SettingsDetailHVMLicenceAvailableVersion    OBJECT-TYPE
    SYNTAX    DisplayString (SIZE(0..40))
    MAX-ACCESS    read-only
    STATUS    current
    DESCRIPTION    "This shows the HVM licence of detailed server blade8 (available version). "
    ::= { blade8Settings 3 }

blade8SettingsManagementPortIPAddress    OBJECT-TYPE
    SYNTAX    DisplayString (SIZE(0..40))
    MAX-ACCESS    read-only
    STATUS    current
    DESCRIPTION    "This shows the IP address of management port of server blade8."
    ::= { blade8Settings 4 }

blade8State    OBJECT IDENTIFIER ::= { blade8 4 } 

blade8StateSlotNum    OBJECT-TYPE
    SYNTAX    Integer32
    MAX-ACCESS    read-only
    STATUS    current
    DESCRIPTION    "This shows the number of installed slots of server blade8."
    ::= { blade8State 1 }

blade8StatePower    OBJECT-TYPE
    SYNTAX    INTEGER {
    poweroff (1), standby (2), poweron (3), unknown (4),poweron-executing (5),poweroff-executing (6)
    }
    MAX-ACCESS    read-only
    STATUS    current
    DESCRIPTION    "This shows the power supply state of server blade8."
    ::= { blade8State 2 }

blade8StateHealth    OBJECT-TYPE
    SYNTAX    INTEGER {
    normal (1),fail (2),unknown (3)
    }
    MAX-ACCESS    read-only
    STATUS    current
    DESCRIPTION    "This shows the health state of server blade8."
    ::= { blade8State 3 }

blade8StatePrimaly    OBJECT-TYPE
    SYNTAX    INTEGER {
    primary(1), non-primary(2),unknown(3)
    }
    MAX-ACCESS    read-only
    STATUS    current
    DESCRIPTION    "This shows the primary state of server blade8."
    ::= { blade8State 4 }

blade8StateCurrentVoltage    OBJECT-TYPE
    SYNTAX    Integer32
    UNITS    "0.1 V"
    MAX-ACCESS    read-only
    STATUS    current
    DESCRIPTION    "This shows the current voltage of server blade8."
    ::= { blade8State 5 }

blade8StateConsumptionCurrent    OBJECT-TYPE
    SYNTAX    Integer32
    UNITS    "0.1 A"
    MAX-ACCESS    read-only
    STATUS    current
    DESCRIPTION    "This shows the consumption current of server blade8."
    ::= { blade8State 6 }

blade8StatePowerConsumption    OBJECT-TYPE
    SYNTAX    Integer32
    UNITS    "W"
    MAX-ACCESS    read-only
    STATUS    current
    DESCRIPTION    "This shows the power consumption of server blade8."
    ::= { blade8State 7 }

blade8StateIntakeTemp    OBJECT-TYPE
    SYNTAX    INTEGER {
    normal (1), higher-warning (2), higher-error (3), lower-warning (4), unknown(5)
    }
    MAX-ACCESS    read-only
    STATUS    current
    DESCRIPTION    "This shows the state of intake temperature of server blade8."
    ::= { blade8State 8 }

blade8StateLEDTable    OBJECT-TYPE
    SYNTAX SEQUENCE OF blade8StateLEDEntry
    MAX-ACCESS not-accessible
    STATUS     current
    DESCRIPTION "This shows the table of LED of server blade8."
    ::= { blade8State 9 }

blade8StateLEDEntry    OBJECT-TYPE
    SYNTAX Blade8StateLEDEntry
    MAX-ACCESS not-accessible
    STATUS    current
    DESCRIPTION "This shows the entry of LED of server blade8."
    INDEX { blade8StateLEDIndex }
    ::= { blade8StateLEDTable 1 }

blade8StateLEDIndex    OBJECT-TYPE
    SYNTAX    Integer32
    MAX-ACCESS    read-only
    STATUS    current
    DESCRIPTION    "This shows the index of LED of server blade8."
    ::= { blade8StateLEDEntry 1 }

blade8StateLEDName    OBJECT-TYPE
    SYNTAX    DisplayString (SIZE(0..40))
    MAX-ACCESS    read-only
    STATUS    current
    DESCRIPTION    "This shows the name of LED of server blade8."
    ::= { blade8StateLEDEntry 2 }

blade8StateLEDState    OBJECT-TYPE
    SYNTAX    INTEGER {
    turn-off(1), turn-on(2),  unknown(3), blink(4), blink-fast(5), blink-slow(6)
    }
    MAX-ACCESS    read-only
    STATUS    current
    DESCRIPTION    "This shows the state of LED of server blade8."
    ::= { blade8StateLEDEntry 3 }

blade8StateLEDColor    OBJECT-TYPE
    SYNTAX    INTEGER {
    blue (1),green (2),red (3),amber (4),unknown (5)
    }
    MAX-ACCESS    read-only
    STATUS    current
    DESCRIPTION    "This shows the color of LED of server blade8."
    ::= { blade8StateLEDEntry 4 }

Blade8StateLEDEntry ::= SEQUENCE {
    blade8StateLEDIndex
        Integer32,
    blade8StateLEDName
        DisplayString,
    blade8StateLEDState
        INTEGER,
    blade8StateLEDColor
        INTEGER
}

blade8StateOther    OBJECT IDENTIFIER ::= { blade8State 20 } 

blade8MaintMode    OBJECT-TYPE
    SYNTAX    INTEGER {
    Normal(1), CE-Maint-mode(2), User-Maint-mode(3), unknown(4)
    }
    MAX-ACCESS    read-only
    STATUS    current
    DESCRIPTION    "This shows the maintenance mode of server blade8."
    ::= { blade8StateOther 1 }

blade8Install    OBJECT IDENTIFIER ::= { blade8State 30 } 

blade8InsCPUSocketTable    OBJECT-TYPE
    SYNTAX SEQUENCE OF blade8InsCPUSocketEntry
    MAX-ACCESS not-accessible
    STATUS     current
    DESCRIPTION "This shows the table of CPU socket of server blade8."
    ::= { blade8Install 1 }

blade8InsCPUSocketEntry    OBJECT-TYPE
    SYNTAX Blade8InsCPUSocketEntry
    MAX-ACCESS not-accessible
    STATUS    current
    DESCRIPTION "This shows the entry of CPU socket of server blade8."
    INDEX { blade8InsCPUSocketIndex }
    ::= { blade8InsCPUSocketTable 1 }

blade8InsCPUSocketIndex    OBJECT-TYPE
    SYNTAX    Integer32
    MAX-ACCESS    read-only
    STATUS    current
    DESCRIPTION    "This shows the index of CPU socket of server blade8."
    ::= { blade8InsCPUSocketEntry 1 }

blade8InsCPUSocketNum    OBJECT-TYPE
    SYNTAX    Integer32
    MAX-ACCESS    read-only
    STATUS    current
    DESCRIPTION    "This shows the number of CPU sockets of server blade8."
    ::= { blade8InsCPUSocketEntry 2 }

blade8InsCPUSocketExist    OBJECT-TYPE
    SYNTAX    INTEGER {
    non-exist(1), exist(2), unknown(3)
    }
    MAX-ACCESS    read-only
    STATUS    current
    DESCRIPTION    "This shows the registrated state of CPU socket of server blade8."
    ::= { blade8InsCPUSocketEntry 3 }

blade8InsCPUSocketCPUName    OBJECT-TYPE
    SYNTAX    DisplayString (SIZE(0..40))
    MAX-ACCESS    read-only
    STATUS    current
    DESCRIPTION    "This shows the CPU name of CPU socket of server blade8."
    ::= { blade8InsCPUSocketEntry 4 }

blade8InsCPUSocketCPUFrequency    OBJECT-TYPE
    SYNTAX    Integer32
    UNITS    "MHz"
    MAX-ACCESS    read-only
    STATUS    current
    DESCRIPTION    "This shows the CPU frequency of CPU socket of server blade8."
    ::= { blade8InsCPUSocketEntry 5 }

blade8InsCPUSocketCPUStepping    OBJECT-TYPE
    SYNTAX    DisplayString 
    MAX-ACCESS    read-only
    STATUS    current
    DESCRIPTION    "This shows the CPU stepping of CPU socket of server blade8."
    ::= { blade8InsCPUSocketEntry 6 }

blade8InsCPUSocketCPUCoreNum    OBJECT-TYPE
    SYNTAX    Integer32
    MAX-ACCESS    read-only
    STATUS    current
    DESCRIPTION    "This shows the CPU core number of CPU socket of server blade8."
    ::= { blade8InsCPUSocketEntry 7 }

blade8InsCPUSocketCPUUpperLimitTemp    OBJECT-TYPE
    SYNTAX    Integer32
    UNITS    "0.1 degrees C"
    MAX-ACCESS    read-only
    STATUS    current
    DESCRIPTION    "This shows the maximum limited CPU temperature of server blade8."
    ::= { blade8InsCPUSocketEntry 8 }

blade8InsCPUSocketCPULowerLimitTemp    OBJECT-TYPE
    SYNTAX    Integer32
    UNITS    "0.1 degrees C"
    MAX-ACCESS    read-only
    STATUS    current
    DESCRIPTION    "This shows the minimum limited CPU temperature of server blade8."
    ::= { blade8InsCPUSocketEntry 9 }

blade8InsDIMMCapacity    OBJECT-TYPE
    SYNTAX    Integer32
    UNITS    "GB"
    MAX-ACCESS    read-only
    STATUS    current
    DESCRIPTION    "This shows the total amount of DIMM capacity of server blade8."
    ::= { blade8Install 2 }

Blade8InsCPUSocketEntry ::= SEQUENCE {
    blade8InsCPUSocketIndex
        Integer32,
    blade8InsCPUSocketNum
        Integer32,
    blade8InsCPUSocketExist
        INTEGER,
    blade8InsCPUSocketCPUName
        DisplayString,
    blade8InsCPUSocketCPUFrequency
        Integer32,
    blade8InsCPUSocketCPUStepping
        DisplayString,
    blade8InsCPUSocketCPUCoreNum
        Integer32,
    blade8InsCPUSocketCPUUpperLimitTemp
        Integer32,
    blade8InsCPUSocketCPULowerLimitTemp
        Integer32,
    blade8InsDIMMCapacity
        Integer32
}

blade8InsDIMMSlotTable    OBJECT-TYPE
    SYNTAX SEQUENCE OF blade8InsDIMMSlotEntry
    MAX-ACCESS not-accessible
    STATUS     current
    DESCRIPTION "This shows the table of DIMM slot of server blade8."
    ::= { blade8Install 3 }

blade8InsDIMMSlotEntry    OBJECT-TYPE
    SYNTAX Blade8InsDIMMSlotEntry
    MAX-ACCESS not-accessible
    STATUS    current
    DESCRIPTION "This shows the entry of DIMM slot of server blade8."
    INDEX { blade8InsDIMMSlotIndex }
    ::= { blade8InsDIMMSlotTable 1 }

blade8InsDIMMSlotIndex    OBJECT-TYPE
    SYNTAX    Integer32
    MAX-ACCESS    read-only
    STATUS    current
    DESCRIPTION    "This shows the index of DIMM slot of server blade8."
    ::= { blade8InsDIMMSlotEntry 1 }

blade8InsDIMMSlotExist    OBJECT-TYPE
    SYNTAX    INTEGER {
    non-exist(1), exist(2), unknown(3)
    }
    MAX-ACCESS    read-only
    STATUS    current
    DESCRIPTION    "This shows the registrated state of DIMM slot of server blade8."
    ::= { blade8InsDIMMSlotEntry 2 }

blade8InsDIMMSlotDIMMCapacity    OBJECT-TYPE
    SYNTAX    Integer32
    UNITS    "GB"
    MAX-ACCESS    read-only
    STATUS    current
    DESCRIPTION    "This shows the capacity of DIMM slots of server blade8."
    ::= { blade8InsDIMMSlotEntry 3 }

blade8InsDIMMSlotDIMMType    OBJECT-TYPE
    SYNTAX    DisplayString 
    MAX-ACCESS    read-only
    STATUS    current
    DESCRIPTION    "This shows the DIMM type of DIMM slot of server blade8."
    ::= { blade8InsDIMMSlotEntry 4 }

blade8InsDIMMSlotDIMMFrequency    OBJECT-TYPE
    SYNTAX    Integer32
    UNITS    "MHz"
    MAX-ACCESS    read-only
    STATUS    current
    DESCRIPTION    "This shows the DIMM frequency of DIMM slot of server blade8."
    ::= { blade8InsDIMMSlotEntry 5 }

blade8InsDIMMSlotDIMMCasLatency    OBJECT-TYPE
    SYNTAX    Integer32
    MAX-ACCESS    read-only
    STATUS    current
    DESCRIPTION    "This shows the DIMM cas latency of DIMM slot of server blade8."
    ::= { blade8InsDIMMSlotEntry 6 }

blade8InsDIMMSlotDIMMStatus    OBJECT-TYPE
    SYNTAX    INTEGER {
    normal (1),unknown (2),degenerated (3),planned-degenerated (4)
    }
    MAX-ACCESS    read-only
    STATUS    current
    DESCRIPTION    "This shows the DIMM state of DIMM slot of server blade8."
    ::= { blade8InsDIMMSlotEntry 7 }

Blade8InsDIMMSlotEntry ::= SEQUENCE {
    blade8InsDIMMSlotIndex
        Integer32,
    blade8InsDIMMSlotExist
        INTEGER,
    blade8InsDIMMSlotDIMMCapacity
        Integer32,
    blade8InsDIMMSlotDIMMType
        DisplayString,
    blade8InsDIMMSlotDIMMFrequency
        Integer32,
    blade8InsDIMMSlotDIMMCasLatency
        Integer32,
    blade8InsDIMMSlotDIMMStatus
        INTEGER
}

blade8InsPCISlotTable    OBJECT-TYPE
    SYNTAX SEQUENCE OF blade8InsPCISlotEntry
    MAX-ACCESS not-accessible
    STATUS     current
    DESCRIPTION "This shows the table of PCI slot of server blade8."
    ::= { blade8Install 4 }

blade8InsPCISlotEntry    OBJECT-TYPE
    SYNTAX Blade8InsPCISlotEntry
    MAX-ACCESS not-accessible
    STATUS    current
    DESCRIPTION "This shows the entry of PCI slot of server blade8."
    INDEX { blade8InsPCISlotIndex }
    ::= { blade8InsPCISlotTable 1 }

blade8InsPCISlotIndex    OBJECT-TYPE
    SYNTAX    Integer32
    MAX-ACCESS    read-only
    STATUS    current
    DESCRIPTION    "This shows the index of PCI slot of server blade8."
    ::= { blade8InsPCISlotEntry 1 }

blade8InsPCISlotType    OBJECT-TYPE
    SYNTAX    DisplayString 
    MAX-ACCESS    read-only
    STATUS    current
    DESCRIPTION    "This shows the type of PCI slot of server blade8."
    ::= { blade8InsPCISlotEntry 2 }

blade8InsPCISlotExist    OBJECT-TYPE
    SYNTAX    INTEGER {
    non-exist(1), exist(2), unknown(3)
    }
    MAX-ACCESS    read-only
    STATUS    current
    DESCRIPTION    "This shows the registrated state of PCI slot of server blade8."
    ::= { blade8InsPCISlotEntry 3 }

blade8InsPCISlotPCIType    OBJECT-TYPE
    SYNTAX    DisplayString 
    MAX-ACCESS    read-only
    STATUS    current
    DESCRIPTION    "This shows the PCI type of PCI slot of server blade8."
    ::= { blade8InsPCISlotEntry 4 }

blade8InsPCISlotPCIProductName    OBJECT-TYPE
    SYNTAX    DisplayString 
    MAX-ACCESS    read-only
    STATUS    current
    DESCRIPTION    "This shows the PCI product name of PCI slot of server blade8."
    ::= { blade8InsPCISlotEntry 5 }

blade8InsPCISlotPCISerial    OBJECT-TYPE
    SYNTAX    DisplayString 
    MAX-ACCESS    read-only
    STATUS    current
    DESCRIPTION    "This shows the serial number of PCI slot of server blade8."
    ::= { blade8InsPCISlotEntry 6 }

blade8InsPCISlotPCIManufacturer    OBJECT-TYPE
    SYNTAX    DisplayString 
    MAX-ACCESS    read-only
    STATUS    current
    DESCRIPTION    "This shows the manufacturer of PCI slot of server blade8."
    ::= { blade8InsPCISlotEntry 7 }

blade8InsPCISlotNum    OBJECT-TYPE
    SYNTAX    Integer32
    MAX-ACCESS    read-only
    STATUS    current
    DESCRIPTION    "This shows the number of PCI slots of server blade8."
    ::= { blade8InsPCISlotEntry 8 }

Blade8InsPCISlotEntry ::= SEQUENCE {
    blade8InsPCISlotIndex
        Integer32,
    blade8InsPCISlotType
        DisplayString,
    blade8InsPCISlotExist
        INTEGER,
    blade8InsPCISlotPCIType
        DisplayString,
    blade8InsPCISlotPCIProductName
        DisplayString,
    blade8InsPCISlotPCISerial
        DisplayString,
    blade8InsPCISlotPCIManufacturer
        DisplayString,
    blade8InsPCISlotNum
        Integer32
}

blade8InsLOMTable    OBJECT-TYPE
    SYNTAX SEQUENCE OF blade8InsLOMEntry
    MAX-ACCESS not-accessible
    STATUS     current
    DESCRIPTION "This shows the table of onboard LAN of server blade8."
    ::= { blade8Install 5 }

blade8InsLOMEntry    OBJECT-TYPE
    SYNTAX Blade8InsLOMEntry
    MAX-ACCESS not-accessible
    STATUS    current
    DESCRIPTION "This shows the entry of onboard LAN of server blade8."
    INDEX { blade8InsLOMIndex }
    ::= { blade8InsLOMTable 1 }

blade8InsLOMIndex    OBJECT-TYPE
    SYNTAX    Integer32
    MAX-ACCESS    read-only
    STATUS    current
    DESCRIPTION    "This shows the index of onboard LAN of server blade8."
    ::= { blade8InsLOMEntry 1 }

blade8InsLOMType    OBJECT-TYPE
    SYNTAX    DisplayString 
    MAX-ACCESS    read-only
    STATUS    current
    DESCRIPTION    "This shows the type of onboard LAN of server blade8."
    ::= { blade8InsLOMEntry 2 }

blade8InsLOMLinkSpeed    OBJECT-TYPE
    SYNTAX    Integer32
    UNITS    "bps"
    MAX-ACCESS    read-only
    STATUS    current
    DESCRIPTION    "This shows the link speed of onboard LAN of server blade8."
    ::= { blade8InsLOMEntry 3 }

blade8InsLOMMAC    OBJECT-TYPE
    SYNTAX    DisplayString 
    MAX-ACCESS    read-only
    STATUS    current
    DESCRIPTION    "This shows the MAC address of onboard LAN of server blade8."
    ::= { blade8InsLOMEntry 4 }

blade8InsLOMLinkStatus    OBJECT-TYPE
    SYNTAX    INTEGER {
    up (1),down (2),unknown (3)
    }
    MAX-ACCESS    read-only
    STATUS    current
    DESCRIPTION    "This shows the link state of onboard LAN of server blade8."
    ::= { blade8InsLOMEntry 5 }

blade8InsLOMPortDivide    OBJECT-TYPE
    SYNTAX    INTEGER {
    possible (1),Impossible (2),unknown (3)
    }
    MAX-ACCESS    read-only
    STATUS    current
    DESCRIPTION    "This shows the port divide propriety of onboard LAN of server blade8."
    ::= { blade8InsLOMEntry 6 }

blade8InsLOMPortDivideNum    OBJECT-TYPE
    SYNTAX    Integer32
    MAX-ACCESS    read-only
    STATUS    current
    DESCRIPTION    "This shows the port divide number of onboard LAN of server blade8."
    ::= { blade8InsLOMEntry 7 }

Blade8InsLOMEntry ::= SEQUENCE {
    blade8InsLOMIndex
        Integer32,
    blade8InsLOMType
        DisplayString,
    blade8InsLOMLinkSpeed
        Integer32,
    blade8InsLOMMAC
        DisplayString,
    blade8InsLOMLinkStatus
        INTEGER,
    blade8InsLOMPortDivide
        INTEGER,
    blade8InsLOMPortDivideNum
        Integer32
}

blade8HDDSlotTable    OBJECT-TYPE
    SYNTAX SEQUENCE OF blade8HDDSlotEntry
    MAX-ACCESS not-accessible
    STATUS     current
    DESCRIPTION "This shows the table of HDD slot of server blade8."
    ::= { blade8Install 7 }

blade8HDDSlotEntry    OBJECT-TYPE
    SYNTAX Blade8HDDSlotEntry
    MAX-ACCESS not-accessible
    STATUS    current
    DESCRIPTION "This shows the entry of HDD slot of server blade8."
    INDEX { blade8HDDSlotIndex }
    ::= { blade8HDDSlotTable 1 }

blade8HDDSlotIndex    OBJECT-TYPE
    SYNTAX    Integer32
    MAX-ACCESS    read-only
    STATUS    current
    DESCRIPTION    "This shows the index of HDD slot of server blade8."
    ::= { blade8HDDSlotEntry 1 }

blade8HDDSlotNum    OBJECT-TYPE
    SYNTAX    Integer32
    MAX-ACCESS    read-only
    STATUS    current
    DESCRIPTION    "This shows the number of HDD slots of server blade8."
    ::= { blade8HDDSlotEntry 2 }

blade8HDDSlotExist    OBJECT-TYPE
    SYNTAX    INTEGER {
    non-exist(1), exist(2), unknown(3)
    }
    MAX-ACCESS    read-only
    STATUS    current
    DESCRIPTION    "This shows the registrated state of HDD slot of server blade8."
    ::= { blade8HDDSlotEntry 3 }

blade8HDDSlotHDDType    OBJECT-TYPE
    SYNTAX    DisplayString 
    MAX-ACCESS    read-only
    STATUS    current
    DESCRIPTION    "This shows the HDD type of HDD slot of server blade8."
    ::= { blade8HDDSlotEntry 4 }

blade8HDDSlotHDDProductName    OBJECT-TYPE
    SYNTAX    DisplayString 
    MAX-ACCESS    read-only
    STATUS    current
    DESCRIPTION    "This shows the HDD product name of HDD slot of server blade8."
    ::= { blade8HDDSlotEntry 5 }

blade8HDDSlotHDDModel    OBJECT-TYPE
    SYNTAX    DisplayString 
    MAX-ACCESS    read-only
    STATUS    current
    DESCRIPTION    "This shows the HDD model of HDD slot of server blade8."
    ::= { blade8HDDSlotEntry 6 }

blade8HDDSlotHDDSerialNum    OBJECT-TYPE
    SYNTAX    DisplayString 
    MAX-ACCESS    read-only
    STATUS    current
    DESCRIPTION    "This shows the HDD serial number of HDD slot of server blade8."
    ::= { blade8HDDSlotEntry 7 }

blade8HDDSlotHDDCapacity    OBJECT-TYPE
    SYNTAX    Integer32
    UNITS    "GB"
    MAX-ACCESS    read-only
    STATUS    current
    DESCRIPTION    "This shows the HDD capacity of HDD slots of server blade8."
    ::= { blade8HDDSlotEntry 8 }

blade8HDDSlotHDDRPM    OBJECT-TYPE
    SYNTAX    Integer32
    UNITS    "rpm"
    MAX-ACCESS    read-only
    STATUS    current
    DESCRIPTION    "This shows the HDD drive speed of HDD slot of server blade8."
    ::= { blade8HDDSlotEntry 9 }

blade8HDDSlotHDDStatePower    OBJECT-TYPE
    SYNTAX    INTEGER {
    poweroff (1), poweron (2), unknown (3)
    }
    MAX-ACCESS    read-only
    STATUS    current
    DESCRIPTION    "This shows the HDD power supply state of HDD slot of server blade8."
    ::= { blade8HDDSlotEntry 10 }

blade8HDDSlotHDDStateHealth    OBJECT-TYPE
    SYNTAX    INTEGER {
    normal (1),fail (2),unknown (3),rebuild (4)
    }
    MAX-ACCESS    read-only
    STATUS    current
    DESCRIPTION    "This shows the HDD health state of HDD slot of server blade8."
    ::= { blade8HDDSlotEntry 11 }

blade8HDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade8(activity)."
    ::= { blade8HDDSlotEntry 12 }

blade8HDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of HDD slot of server blade8(status)."
    ::= { blade8HDDSlotEntry 13 }

blade8HDDSlotHDDFWInfoName    OBJECT-TYPE
    SYNTAX    DisplayString 
    MAX-ACCESS    read-only
    STATUS    current
    DESCRIPTION    "This shows the HDD firmware name of HDD slot of server blade8."
    ::= { blade8HDDSlotEntry 20 }

blade8HDDSlotHDDFWInfoCurrentVer    OBJECT-TYPE
    SYNTAX    DisplayString 
    MAX-ACCESS    read-only
    STATUS    current
    DESCRIPTION    "This shows the HDD firmware current version of HDD slot of server blade8."
    ::= { blade8HDDSlotEntry 21 }

blade8HDDSlotHDDFWInfoNextVer    OBJECT-TYPE
    SYNTAX    DisplayString 
    MAX-ACCESS    read-only
    STATUS    current
    DESCRIPTION    "This shows the HDD firmware next version of HDD slot of server blade8."
    ::= { blade8HDDSlotEntry 22 }

Blade8HDDSlotEntry ::= SEQUENCE {
    blade8HDDSlotIndex
        Integer32,
    blade8HDDSlotNum
        Integer32,
    blade8HDDSlotExist
        INTEGER,
    blade8HDDSlotHDDType
        DisplayString,
    blade8HDDSlotHDDProductName
        DisplayString,
    blade8HDDSlotHDDModel
        DisplayString,
    blade8HDDSlotHDDSerialNum
        DisplayString,
    blade8HDDSlotHDDCapacity
        Integer32,
    blade8HDDSlotHDDRPM
        Integer32,
    blade8HDDSlotHDDStatePower
        INTEGER,
    blade8HDDSlotHDDStateHealth
        INTEGER,
    blade8HDDSlotHDDStateLEDACT
        INTEGER,
    blade8HDDSlotHDDStateLEDSTS
        INTEGER,
    blade8HDDSlotHDDFWInfoName
        DisplayString,
    blade8HDDSlotHDDFWInfoCurrentVer
        DisplayString,
    blade8HDDSlotHDDFWInfoNextVer
        DisplayString
}

blade8ExpansionHDDSlotTable    OBJECT-TYPE
    SYNTAX SEQUENCE OF blade8ExpansionHDDSlotEntry
    MAX-ACCESS not-accessible
    STATUS     current
    DESCRIPTION "This shows the table of expansion HDD slot of server blade8."
    ::= { blade8Install 8 }

blade8ExpansionHDDSlotEntry    OBJECT-TYPE
    SYNTAX Blade8ExpansionHDDSlotEntry
    MAX-ACCESS not-accessible
    STATUS    current
    DESCRIPTION "This shows the entry of expansion HDD slot of server blade8."
    INDEX { blade8ExpansionHDDSlotIndex }
    ::= { blade8ExpansionHDDSlotTable 1 }

blade8ExpansionHDDSlotIndex    OBJECT-TYPE
    SYNTAX    Integer32
    MAX-ACCESS    read-only
    STATUS    current
    DESCRIPTION    "This shows the index of expansion HDD slot of server blade8."
    ::= { blade8ExpansionHDDSlotEntry 1 }

blade8ExpansionHDDSlotNum    OBJECT-TYPE
    SYNTAX    Integer32
    MAX-ACCESS    read-only
    STATUS    current
    DESCRIPTION    "This shows the number of expansion HDD slots of server blade8."
    ::= { blade8ExpansionHDDSlotEntry 2 }

blade8ExpansionHDDSlotExist    OBJECT-TYPE
    SYNTAX    INTEGER {
    non-exist(1), exist(2), unknown(3)
    }
    MAX-ACCESS    read-only
    STATUS    current
    DESCRIPTION    "This shows the registrated state of expansion HDD slot of server blade8."
    ::= { blade8ExpansionHDDSlotEntry 3 }

blade8ExpansionHDDSlotHDDType    OBJECT-TYPE
    SYNTAX    DisplayString 
    MAX-ACCESS    read-only
    STATUS    current
    DESCRIPTION    "This shows the HDD type of expansion HDD slot of server blade8."
    ::= { blade8ExpansionHDDSlotEntry 4 }

blade8ExpansionHDDSlotHDDProductName    OBJECT-TYPE
    SYNTAX    DisplayString 
    MAX-ACCESS    read-only
    STATUS    current
    DESCRIPTION    "This shows the HDD product name of expansion HDD slot of server blade8."
    ::= { blade8ExpansionHDDSlotEntry 5 }

blade8ExpansionHDDSlotHDDModel    OBJECT-TYPE
    SYNTAX    DisplayString 
    MAX-ACCESS    read-only
    STATUS    current
    DESCRIPTION    "This shows the HDD model of expansion HDD slot of server blade8."
    ::= { blade8ExpansionHDDSlotEntry 6 }

blade8ExpansionHDDSlotHDDSerialNum    OBJECT-TYPE
    SYNTAX    DisplayString 
    MAX-ACCESS    read-only
    STATUS    current
    DESCRIPTION    "This shows the HDD serial number of expansion HDD slot of server blade8."
    ::= { blade8ExpansionHDDSlotEntry 7 }

blade8ExpansionHDDSlotHDDCapacity    OBJECT-TYPE
    SYNTAX    Integer32
    UNITS    "GB"
    MAX-ACCESS    read-only
    STATUS    current
    DESCRIPTION    "This shows the HDD capacity of expansion HDD slots of server blade8."
    ::= { blade8ExpansionHDDSlotEntry 8 }

blade8ExpansionHDDSlotHDDRPM    OBJECT-TYPE
    SYNTAX    Integer32
    UNITS    "rpm"
    MAX-ACCESS    read-only
    STATUS    current
    DESCRIPTION    "This shows the HDD drive speed of expansion HDD slot of server blade8."
    ::= { blade8ExpansionHDDSlotEntry 9 }

blade8ExpansionHDDSlotHDDStatePower    OBJECT-TYPE
    SYNTAX    INTEGER {
    poweroff (1), poweron (2), unknown (3)
    }
    MAX-ACCESS    read-only
    STATUS    current
    DESCRIPTION    "This shows the HDD power supply state of expansion HDD slot of server blade8."
    ::= { blade8ExpansionHDDSlotEntry 10 }

blade8ExpansionHDDSlotHDDStateHealth    OBJECT-TYPE
    SYNTAX    INTEGER {
    normal (1),fail (2),unknown (3),rebuild (4)
    }
    MAX-ACCESS    read-only
    STATUS    current
    DESCRIPTION    "This shows the HDD health state of expansion HDD slot of server blade8."
    ::= { blade8ExpansionHDDSlotEntry 11 }

blade8ExpansionHDDSlotHDDStateLEDACT    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade8(activity)."
    ::= { blade8ExpansionHDDSlotEntry 12 }

blade8ExpansionHDDSlotHDDStateLEDSTS    OBJECT-TYPE
    SYNTAX    INTEGER {
    turn-off(1), turn-on(2),  unknown(3), blink(4), blink-fast(5), blink-slow(6)
    }
    MAX-ACCESS    read-only
    STATUS    current
    DESCRIPTION    "This shows the LED state of expansion HDD slot of server blade8(status)."
    ::= { blade8ExpansionHDDSlotEntry 13 }

blade8ExpansionHDDSlotHDDFWInfoName    OBJECT-TYPE
    SYNTAX    DisplayString 
    MAX-ACCESS    read-only
    STATUS    current
    DESCRIPTION    "This shows the HDD firmware name of expansion HDD slot of server blade8."
    ::= { blade8ExpansionHDDSlotEntry 20 }

blade8ExpansionHDDSlotHDDFWInfoCurrentVer    OBJECT-TYPE
    SYNTAX    DisplayString 
    MAX-ACCESS    read-only
    STATUS    current
    DESCRIPTION    "This shows the HDD firmware current version of expansion HDD slot of server blade8."
    ::= { blade8ExpansionHDDSlotEntry 21 }

blade8ExpansionHDDSlotHDDFWInfoNextVer    OBJECT-TYPE
    SYNTAX    DisplayString 
    MAX-ACCESS    read-only
    STATUS    current
    DESCRIPTION    "This shows the HDD firmware next version of expansion HDD slot of server blade8."
    ::= { blade8ExpansionHDDSlotEntry 22 }

Blade8ExpansionHDDSlotEntry ::= SEQUENCE {
    blade8ExpansionHDDSlotIndex
        Integer32,
    blade8ExpansionHDDSlotNum
        Integer32,
    blade8ExpansionHDDSlotExist
        INTEGER,
    blade8ExpansionHDDSlotHDDType
        DisplayString,
    blade8ExpansionHDDSlotHDDProductName
        DisplayString,
    blade8ExpansionHDDSlotHDDModel
        DisplayString,
    blade8ExpansionHDDSlotHDDSerialNum
        DisplayString,
    blade8ExpansionHDDSlotHDDCapacity
        Integer32,
    blade8ExpansionHDDSlotHDDRPM
        Integer32,
    blade8ExpansionHDDSlotHDDStatePower
        INTEGER,
    blade8ExpansionHDDSlotHDDStateHealth
        INTEGER,
    blade8ExpansionHDDSlotHDDStateLEDACT
        INTEGER,
    blade8ExpansionHDDSlotHDDStateLEDSTS
        INTEGER,
    blade8ExpansionHDDSlotHDDFWInfoName
        DisplayString,
    blade8ExpansionHDDSlotHDDFWInfoCurrentVer
        DisplayString,
    blade8ExpansionHDDSlotHDDFWInfoNextVer
        DisplayString
}

blade8VoltageSensorTable    OBJECT-TYPE
    SYNTAX SEQUENCE OF blade8VoltageSensorEntry
    MAX-ACCESS not-accessible
    STATUS     current
    DESCRIPTION "This shows the table of voltage sensor of server blade8."
    ::= { blade8State 40 }

blade8VoltageSensorEntry    OBJECT-TYPE
    SYNTAX Blade8VoltageSensorEntry
    MAX-ACCESS not-accessible
    STATUS    current
    DESCRIPTION "This shows the entry of voltage sensor of server blade8."
    INDEX { blade8VoltageSensorIndex }
    ::= { blade8VoltageSensorTable 1 }

blade8VoltageSensorIndex    OBJECT-TYPE
    SYNTAX    Integer32
    MAX-ACCESS    read-only
    STATUS    current
    DESCRIPTION    "This shows the index of voltage sensor of server blade8."
    ::= { blade8VoltageSensorEntry 1 }

blade8VoltageSensorName    OBJECT-TYPE
    SYNTAX    DisplayString 
    MAX-ACCESS    read-only
    STATUS    current
    DESCRIPTION    "This shows the voltage sensor name of server blade8."
    ::= { blade8VoltageSensorEntry 2 }

blade8VoltageSensorValue    OBJECT-TYPE
    SYNTAX    Integer32
    UNITS    "0.1 V"
    MAX-ACCESS    read-only
    STATUS    current
    DESCRIPTION    "This shows the voltage sensor value of server blade8."
    ::= { blade8VoltageSensorEntry 3 }

blade8VoltageSensorValid    OBJECT-TYPE
    SYNTAX    INTEGER {
    invalid (1),valid (2),unknown (3)
    }
    MAX-ACCESS    read-only
    STATUS    current
    DESCRIPTION    "This shows the validity of voltage sensor value of server blade8."
    ::= { blade8VoltageSensorEntry 4 }

Blade8VoltageSensorEntry ::= SEQUENCE {
    blade8VoltageSensorIndex
        Integer32,
    blade8VoltageSensorName
        DisplayString,
    blade8VoltageSensorValue
        Integer32,
    blade8VoltageSensorValid
        INTEGER
}

blade8TempSensorTable    OBJECT-TYPE
    SYNTAX SEQUENCE OF blade8TempSensorEntry
    MAX-ACCESS not-accessible
    STATUS     current
    DESCRIPTION "This shows the table of temperature sensor of server blade8."
    ::= { blade8State 41 }

blade8TempSensorEntry    OBJECT-TYPE
    SYNTAX Blade8TempSensorEntry
    MAX-ACCESS not-accessible
    STATUS    current
    DESCRIPTION "This shows the entry of temperature sensor of server blade8."
    INDEX { blade8TempSensorIndex }
    ::= { blade8TempSensorTable 1 }

blade8TempSensorIndex    OBJECT-TYPE
    SYNTAX    Integer32
    MAX-ACCESS    read-only
    STATUS    current
    DESCRIPTION    "This shows the index of temperature sensor of server blade8."
    ::= { blade8TempSensorEntry 1 }

blade8TempSensorName    OBJECT-TYPE
    SYNTAX    DisplayString 
    MAX-ACCESS    read-only
    STATUS    current
    DESCRIPTION    "This shows the temperature sensor name of server blade8."
    ::= { blade8TempSensorEntry 2 }

blade8TempSensorValue    OBJECT-TYPE
    SYNTAX    Integer32
    UNITS    "0.1 degrees C"
    MAX-ACCESS    read-only
    STATUS    current
    DESCRIPTION    "This shows the temperature sensor value of server blade8."
    ::= { blade8TempSensorEntry 3 }

blade8TempSensorValid    OBJECT-TYPE
    SYNTAX    INTEGER {
    invalid (1),valid (2),unknown (3)
    }
    MAX-ACCESS    read-only
    STATUS    current
    DESCRIPTION    "This shows the validity of temperature sensor value of server blade8."
    ::= { blade8TempSensorEntry 4 }

Blade8TempSensorEntry ::= SEQUENCE {
    blade8TempSensorIndex
        Integer32,
    blade8TempSensorName
        DisplayString,
    blade8TempSensorValue
        Integer32,
    blade8TempSensorValid
        INTEGER
}

blade8FWInfo    OBJECT IDENTIFIER ::= { blade8 5 } 

blade8FWInfoTotalCurrentVer    OBJECT-TYPE
    SYNTAX    DisplayString (SIZE(0..40))
    MAX-ACCESS    read-only
    STATUS    current
    DESCRIPTION    "This shows the total current version of firmware of server blade8."
    ::= { blade8FWInfo 1 }

blade8FWInfoTotalNextVer    OBJECT-TYPE
    SYNTAX    DisplayString (SIZE(0..40))
    MAX-ACCESS    read-only
    STATUS    current
    DESCRIPTION    "This shows the total next version of firmware of server blade8."
    ::= { blade8FWInfo 2 }

blade8FWInfoTable    OBJECT-TYPE
    SYNTAX SEQUENCE OF blade8FWInfoEntry
    MAX-ACCESS not-accessible
    STATUS     current
    DESCRIPTION "This shows the table of firmware information of server blade8."
    ::= { blade8FWInfo 3 }

blade8FWInfoEntry    OBJECT-TYPE
    SYNTAX Blade8FWInfoEntry
    MAX-ACCESS not-accessible
    STATUS    current
    DESCRIPTION "This shows the entry of firmware information of server blade8."
    INDEX { blade8FWInfoIndex }
    ::= { blade8FWInfoTable 1 }

blade8FWInfoIndex    OBJECT-TYPE
    SYNTAX    Integer32
    MAX-ACCESS    read-only
    STATUS    current
    DESCRIPTION    "This shows the index of firmware information of server blade8."
    ::= { blade8FWInfoEntry 1 }

blade8FWInfoName    OBJECT-TYPE
    SYNTAX    DisplayString (SIZE(0..40))
    MAX-ACCESS    read-only
    STATUS    current
    DESCRIPTION    "This shows the firmware name of server blade8."
    ::= { blade8FWInfoEntry 2 }

blade8FWCurrentVer    OBJECT-TYPE
    SYNTAX    DisplayString (SIZE(0..40))
    MAX-ACCESS    read-only
    STATUS    current
    DESCRIPTION    "This shows the firmware current version of server blade8."
    ::= { blade8FWInfoEntry 3 }

blade8FWInfoNextVer    OBJECT-TYPE
    SYNTAX    DisplayString (SIZE(0..40))
    MAX-ACCESS    read-only
    STATUS    current
    DESCRIPTION    "This shows the firmware next version of server blade8."
    ::= { blade8FWInfoEntry 4 }

blade8FWInfoHVMCurrentVer    OBJECT-TYPE
    SYNTAX    DisplayString (SIZE(0..40))
    MAX-ACCESS    read-only
    STATUS    current
    DESCRIPTION    "This shows the HVM current version of server blade8."
    ::= { blade8FWInfo 4 }

blade8FWInfoHVMNextVer    OBJECT-TYPE
    SYNTAX    DisplayString (SIZE(0..40))
    MAX-ACCESS    read-only
    STATUS    current
    DESCRIPTION    "This shows the HVM next version of server blade8."
    ::= { blade8FWInfo 5 }

Blade8FWInfoEntry ::= SEQUENCE {
    blade8FWInfoIndex
        Integer32,
    blade8FWInfoName
        DisplayString,
    blade8FWCurrentVer
        DisplayString,
    blade8FWInfoNextVer
        DisplayString,
    blade8FWInfoHVMCurrentVer
        DisplayString,
    blade8FWInfoHVMNextVer
        DisplayString
}

managementModule    OBJECT IDENTIFIER ::= { component 2 } 

managementModule1    OBJECT IDENTIFIER ::= { managementModule 1 } 

managementModule1BasicInfo    OBJECT IDENTIFIER ::= { managementModule1 1 } 

mm1InfoProductName    OBJECT-TYPE
    SYNTAX    DisplayString (SIZE(0..40))
    MAX-ACCESS    read-only
    STATUS    current
    DESCRIPTION    "This shows the product name of management module1."
    ::= { managementModule1BasicInfo 1 }

mm1InfoModel    OBJECT-TYPE
    SYNTAX    DisplayString (SIZE(0..40))
    MAX-ACCESS    read-only
    STATUS    current
    DESCRIPTION    "This shows the model name of management module1."
    ::= { managementModule1BasicInfo 2 }

mm1InfoSerialNum    OBJECT-TYPE
    SYNTAX    DisplayString (SIZE(0..40))
    MAX-ACCESS    read-only
    STATUS    current
    DESCRIPTION    "This shows the serial number of management module1."
    ::= { managementModule1BasicInfo 3 }

mm1InfoProductVersion    OBJECT-TYPE
    SYNTAX    DisplayString (SIZE(0..40))
    MAX-ACCESS    read-only
    STATUS    current
    DESCRIPTION    "This shows the product version of management module1."
    ::= { managementModule1BasicInfo 4 }

mm1InfoProductManufacturer    OBJECT-TYPE
    SYNTAX    DisplayString (SIZE(0..40))
    MAX-ACCESS    read-only
    STATUS    current
    DESCRIPTION    "This shows the product manufacturer of management module1."
    ::= { managementModule1BasicInfo 5 }

mm1InfoChassisID    OBJECT-TYPE
    SYNTAX    DisplayString (SIZE(0..40))
    MAX-ACCESS    read-only
    STATUS    current
    DESCRIPTION    "This shows chassis ID of management module1."
    ::= { managementModule1BasicInfo 6 }

mm1InfoBoardProductName    OBJECT-TYPE
    SYNTAX    DisplayString (SIZE(0..40))
    MAX-ACCESS    read-only
    STATUS    current
    DESCRIPTION    "This shows the board product name of management module1. "
    ::= { managementModule1BasicInfo 7 }

mm1InfoBoardSerialNum    OBJECT-TYPE
    SYNTAX    DisplayString (SIZE(0..40))
    MAX-ACCESS    read-only
    STATUS    current
    DESCRIPTION    "This shows the board serial number of management module1. "
    ::= { managementModule1BasicInfo 8 }

mm1InfoBoardManufacturer    OBJECT-TYPE
    SYNTAX    DisplayString (SIZE(0..40))
    MAX-ACCESS    read-only
    STATUS    current
    DESCRIPTION    "This shows the board manufacturer of management module1."
    ::= { managementModule1BasicInfo 9 }

mm1InfoSpec    OBJECT IDENTIFIER ::= { managementModule1BasicInfo 20 } 

mm1SpecPowerConsumption    OBJECT-TYPE
    SYNTAX    Integer32
    UNITS    "W"
    MAX-ACCESS    read-only
    STATUS    current
    DESCRIPTION    "This shows the power consumption of management module1."
    ::= { mm1InfoSpec 1 }

mm1SpecMass    OBJECT-TYPE
    SYNTAX    Integer32
    UNITS    "0.1 kg"
    MAX-ACCESS    read-only
    STATUS    current
    DESCRIPTION    "This shows the weight of management module1."
    ::= { mm1InfoSpec 2 }

mm1SpecUpperLimitTemp    OBJECT-TYPE
    SYNTAX    Integer32
    UNITS    "0.1 degrees C"
    MAX-ACCESS    read-only
    STATUS    current
    DESCRIPTION    "This shows the maximum limied temperature of management module1."
    ::= { mm1InfoSpec 3 }

mm1SpecLowerLimitTemp    OBJECT-TYPE
    SYNTAX    Integer32
    UNITS    "0.1 degrees C"
    MAX-ACCESS    read-only
    STATUS    current
    DESCRIPTION    "This shows the minimum limied temperature of management module1."
    ::= { mm1InfoSpec 4 }

managementModule1Capacity    OBJECT IDENTIFIER ::= { managementModule1 2 } 

mm1CapacityVoltageSensor    OBJECT-TYPE
    SYNTAX    Integer32
    MAX-ACCESS    read-only
    STATUS    current
    DESCRIPTION    "This shows the capacity of voltage sensors of management module1."
    ::= { managementModule1Capacity 1 }

mm1CapacityTempSensor    OBJECT-TYPE
    SYNTAX    Integer32
    MAX-ACCESS    read-only
    STATUS    current
    DESCRIPTION    "This shows the capacity of temperature sensors of management module1."
    ::= { managementModule1Capacity 2 }

mm1CapacityLED    OBJECT-TYPE
    SYNTAX    Integer32
    MAX-ACCESS    read-only
    STATUS    current
    DESCRIPTION    "This shows the capacity of count of LEDs of management module1."
    ::= { managementModule1Capacity 3 }

managementModule1Settings    OBJECT IDENTIFIER ::= { managementModule1 3 } 

mm1SettingsManagementIPAddress    OBJECT-TYPE
    SYNTAX    DisplayString 
    MAX-ACCESS    read-only
    STATUS    current
    DESCRIPTION    "This shows the management LAN IP address of management module1."
    ::= { managementModule1Settings 1 }

mm1SettingsMaintIPAddress    OBJECT-TYPE
    SYNTAX    DisplayString 
    MAX-ACCESS    read-only
    STATUS    current
    DESCRIPTION    "This shows the maintenance LAN IP address of management module1."
    ::= { managementModule1Settings 2 }

managementModule1State    OBJECT IDENTIFIER ::= { managementModule1 4 } 

mm1StateSlotNum    OBJECT-TYPE
    SYNTAX    Integer32
    MAX-ACCESS    read-only
    STATUS    current
    DESCRIPTION    "This shows the number of installed slots of management module1."
    ::= { managementModule1State 1 }

mm1StatePower    OBJECT-TYPE
    SYNTAX    INTEGER {
    poweroff (1), standby (2), poweron (3), unknown (4),poweron-executing (5),poweroff-executing (6)
    }
    MAX-ACCESS    read-only
    STATUS    current
    DESCRIPTION    "This shows the power supply state of management module1."
    ::= { managementModule1State 2 }

mm1StateHealth    OBJECT-TYPE
    SYNTAX    INTEGER {
    normal (1),fail (2),unknown (3)
    }
    MAX-ACCESS    read-only
    STATUS    current
    DESCRIPTION    "This shows the health state of management module1."
    ::= { managementModule1State 3 }

mm1StateActive    OBJECT-TYPE
    SYNTAX    INTEGER {
    active(1), standby(2), unknown(3)
    }
    MAX-ACCESS    read-only
    STATUS    current
    DESCRIPTION    "This shows the operating mode of management module1."
    ::= { managementModule1State 4 }

mm1StateLEDTable    OBJECT-TYPE
    SYNTAX SEQUENCE OF mm1StateLEDEntry
    MAX-ACCESS not-accessible
    STATUS     current
    DESCRIPTION "This shows the table of LED of management module1."
    ::= { managementModule1State 5 }

mm1StateLEDEntry    OBJECT-TYPE
    SYNTAX Mm1StateLEDEntry
    MAX-ACCESS not-accessible
    STATUS    current
    DESCRIPTION "This shows the entry of LED of management module1."
    INDEX { mm1StateLEDIndex }
    ::= { mm1StateLEDTable 1 }

mm1StateLEDIndex    OBJECT-TYPE
    SYNTAX    Integer32
    MAX-ACCESS    read-only
    STATUS    current
    DESCRIPTION    "This shows the index of LED of management module1."
    ::= { mm1StateLEDEntry 1 }

mm1StateLEDName    OBJECT-TYPE
    SYNTAX    DisplayString (SIZE(0..40))
    MAX-ACCESS    read-only
    STATUS    current
    DESCRIPTION    "This shows the name of LED of management module1."
    ::= { mm1StateLEDEntry 2 }

mm1StateLEDState    OBJECT-TYPE
    SYNTAX    INTEGER {
    turn-off(1), turn-on(2),  unknown(3), blink(4), blink-fast(5), blink-slow(6)
    }
    MAX-ACCESS    read-only
    STATUS    current
    DESCRIPTION    "This shows the state of LED of management module1."
    ::= { mm1StateLEDEntry 3 }

mm1StateLEDColor    OBJECT-TYPE
    SYNTAX    INTEGER {
    blue (1),green (2),red (3),amber (4),unknown (5)
    }
    MAX-ACCESS    read-only
    STATUS    current
    DESCRIPTION    "This shows the color of LED of management module1."
    ::= { mm1StateLEDEntry 4 }

Mm1StateLEDEntry ::= SEQUENCE {
    mm1StateLEDIndex
        Integer32,
    mm1StateLEDName
        DisplayString,
    mm1StateLEDState
        INTEGER,
    mm1StateLEDColor
        INTEGER
}

mm1StateOther    OBJECT IDENTIFIER ::= { managementModule1State 20 } 

mm1MaintMode    OBJECT-TYPE
    SYNTAX    INTEGER {
    Normal(1), CE-Maint-mode(2), User-Maint-mode(3), unknown(4)
    }
    MAX-ACCESS    read-only
    STATUS    current
    DESCRIPTION    "This shows the maintenance mode of management module1."
    ::= { mm1StateOther 1 }

mm1VoltageSensorTable    OBJECT-TYPE
    SYNTAX SEQUENCE OF mm1VoltageSensorEntry
    MAX-ACCESS not-accessible
    STATUS     current
    DESCRIPTION "This shows the table of voltage sensor of management module1."
    ::= { managementModule1State 30 }

mm1VoltageSensorEntry    OBJECT-TYPE
    SYNTAX Mm1VoltageSensorEntry
    MAX-ACCESS not-accessible
    STATUS    current
    DESCRIPTION "This shows the entry of voltage sensor of management module1."
    INDEX { mm1VoltageSensorIndex }
    ::= { mm1VoltageSensorTable 1 }

mm1VoltageSensorIndex    OBJECT-TYPE
    SYNTAX    Integer32
    MAX-ACCESS    read-only
    STATUS    current
    DESCRIPTION    "This shows the index of voltage sensor of management module1."
    ::= { mm1VoltageSensorEntry 1 }

mm1VoltageSensorName    OBJECT-TYPE
    SYNTAX    DisplayString (SIZE(0..40))
    MAX-ACCESS    read-only
    STATUS    current
    DESCRIPTION    "This shows the voltage sensor name of management module1."
    ::= { mm1VoltageSensorEntry 2 }

mm1VoltageSensorValue    OBJECT-TYPE
    SYNTAX    Integer32
    UNITS    "0.1 V"
    MAX-ACCESS    read-only
    STATUS    current
    DESCRIPTION    "This shows the voltage sensor value of management module1."
    ::= { mm1VoltageSensorEntry 3 }

mm1VoltageSensorValid    OBJECT-TYPE
    SYNTAX    INTEGER {
    invalid (1),valid (2),unknown (3)
    }
    MAX-ACCESS    read-only
    STATUS    current
    DESCRIPTION    "This shows the validity of voltage sensor value of management module1."
    ::= { mm1VoltageSensorEntry 4 }

Mm1VoltageSensorEntry ::= SEQUENCE {
    mm1VoltageSensorIndex
        Integer32,
    mm1VoltageSensorName
        DisplayString,
    mm1VoltageSensorValue
        Integer32,
    mm1VoltageSensorValid
        INTEGER
}

mm1TempSensorTable    OBJECT-TYPE
    SYNTAX SEQUENCE OF mm1TempSensorEntry
    MAX-ACCESS not-accessible
    STATUS     current
    DESCRIPTION "This shows the table of temperature sensor of management module1."
    ::= { managementModule1State 31 }

mm1TempSensorEntry    OBJECT-TYPE
    SYNTAX Mm1TempSensorEntry
    MAX-ACCESS not-accessible
    STATUS    current
    DESCRIPTION "This shows the entry of temperature sensor of management module1."
    INDEX { mm1TempSensorIndex }
    ::= { mm1TempSensorTable 1 }

mm1TempSensorIndex    OBJECT-TYPE
    SYNTAX    Integer32
    MAX-ACCESS    read-only
    STATUS    current
    DESCRIPTION    "This shows the index of temperature sensor of management module1."
    ::= { mm1TempSensorEntry 1 }

mm1TempSensorName    OBJECT-TYPE
    SYNTAX    DisplayString (SIZE(0..40))
    MAX-ACCESS    read-only
    STATUS    current
    DESCRIPTION    "This shows the temperature sensor name of management module1."
    ::= { mm1TempSensorEntry 2 }

mm1TempSensorValue    OBJECT-TYPE
    SYNTAX    Integer32
    UNITS    "0.1 degrees C"
    MAX-ACCESS    read-only
    STATUS    current
    DESCRIPTION    "This shows the temperature sensor value of management module1."
    ::= { mm1TempSensorEntry 3 }

mm1TempSensorValid    OBJECT-TYPE
    SYNTAX    INTEGER {
    invalid (1),valid (2),unknown (3)
    }
    MAX-ACCESS    read-only
    STATUS    current
    DESCRIPTION    "This shows the validity of temperature sensor value of management module1."
    ::= { mm1TempSensorEntry 4 }

Mm1TempSensorEntry ::= SEQUENCE {
    mm1TempSensorIndex
        Integer32,
    mm1TempSensorName
        DisplayString,
    mm1TempSensorValue
        Integer32,
    mm1TempSensorValid
        INTEGER
}

managementModule1FWInfo    OBJECT IDENTIFIER ::= { managementModule1 5 } 

managementModule1FWInfoTotalVer    OBJECT-TYPE
    SYNTAX    DisplayString (SIZE(0..40))
    MAX-ACCESS    read-only
    STATUS    current
    DESCRIPTION    "This shows the total version of firmware of management module1."
    ::= { managementModule1FWInfo 1 }

managementModule1FWInfoTable    OBJECT-TYPE
    SYNTAX SEQUENCE OF managementModule1FWInfoEntry
    MAX-ACCESS not-accessible
    STATUS     current
    DESCRIPTION "This shows the table of firmware information of management module1."
    ::= { managementModule1FWInfo 2 }

managementModule1FWInfoEntry    OBJECT-TYPE
    SYNTAX ManagementModule1FWInfoEntry
    MAX-ACCESS not-accessible
    STATUS    current
    DESCRIPTION "This shows the entry of firmware information of management module1."
    INDEX { managementModule1FWInfoIndex }
    ::= { managementModule1FWInfoTable 1 }

managementModule1FWInfoIndex    OBJECT-TYPE
    SYNTAX    Integer32
    MAX-ACCESS    read-only
    STATUS    current
    DESCRIPTION    "This shows the index of firmware information of management module1."
    ::= { managementModule1FWInfoEntry 1 }

managementModule1FWInfoName    OBJECT-TYPE
    SYNTAX    DisplayString (SIZE(0..40))
    MAX-ACCESS    read-only
    STATUS    current
    DESCRIPTION    "This shows the firmware name of management module1."
    ::= { managementModule1FWInfoEntry 2 }

managementModule1FWInfoCurrentVer    OBJECT-TYPE
    SYNTAX    DisplayString (SIZE(0..40))
    MAX-ACCESS    read-only
    STATUS    current
    DESCRIPTION    "This shows the firmware current version of management module1."
    ::= { managementModule1FWInfoEntry 3 }

ManagementModule1FWInfoEntry ::= SEQUENCE {
    managementModule1FWInfoIndex
        Integer32,
    managementModule1FWInfoName
        DisplayString,
    managementModule1FWInfoCurrentVer
        DisplayString
}

managementModule2    OBJECT IDENTIFIER ::= { managementModule 2 } 

managementModule2BasicInfo    OBJECT IDENTIFIER ::= { managementModule2 1 } 

mm2InfoProductName    OBJECT-TYPE
    SYNTAX    DisplayString (SIZE(0..40))
    MAX-ACCESS    read-only
    STATUS    current
    DESCRIPTION    "This shows the product name of management module2."
    ::= { managementModule2BasicInfo 1 }

mm2InfoModel    OBJECT-TYPE
    SYNTAX    DisplayString (SIZE(0..40))
    MAX-ACCESS    read-only
    STATUS    current
    DESCRIPTION    "This shows the model name of management module2."
    ::= { managementModule2BasicInfo 2 }

mm2InfoSerialNum    OBJECT-TYPE
    SYNTAX    DisplayString (SIZE(0..40))
    MAX-ACCESS    read-only
    STATUS    current
    DESCRIPTION    "This shows the serial number of management module2."
    ::= { managementModule2BasicInfo 3 }

mm2InfoProductVersion    OBJECT-TYPE
    SYNTAX    DisplayString (SIZE(0..40))
    MAX-ACCESS    read-only
    STATUS    current
    DESCRIPTION    "This shows the product version of management module2."
    ::= { managementModule2BasicInfo 4 }

mm2InfoProductManufacturer    OBJECT-TYPE
    SYNTAX    DisplayString (SIZE(0..40))
    MAX-ACCESS    read-only
    STATUS    current
    DESCRIPTION    "This shows the product manufacturer of management module2."
    ::= { managementModule2BasicInfo 5 }

mm2InfoChassisID    OBJECT-TYPE
    SYNTAX    DisplayString (SIZE(0..40))
    MAX-ACCESS    read-only
    STATUS    current
    DESCRIPTION    "This shows chassis ID of management module2."
    ::= { managementModule2BasicInfo 6 }

mm2InfoBoardProductName    OBJECT-TYPE
    SYNTAX    DisplayString (SIZE(0..40))
    MAX-ACCESS    read-only
    STATUS    current
    DESCRIPTION    "This shows the board product name of management module2. "
    ::= { managementModule2BasicInfo 7 }

mm2InfoBoardSerialNum    OBJECT-TYPE
    SYNTAX    DisplayString (SIZE(0..40))
    MAX-ACCESS    read-only
    STATUS    current
    DESCRIPTION    "This shows the board serial number of management module2. "
    ::= { managementModule2BasicInfo 8 }

mm2InfoBoardManufacturer    OBJECT-TYPE
    SYNTAX    DisplayString (SIZE(0..40))
    MAX-ACCESS    read-only
    STATUS    current
    DESCRIPTION    "This shows the board manufacturer of management module2."
    ::= { managementModule2BasicInfo 9 }

mm2InfoSpec    OBJECT IDENTIFIER ::= { managementModule2BasicInfo 20 } 

mm2SpecPowerConsumption    OBJECT-TYPE
    SYNTAX    Integer32
    UNITS    "W"
    MAX-ACCESS    read-only
    STATUS    current
    DESCRIPTION    "This shows the power consumption of management module2."
    ::= { mm2InfoSpec 1 }

mm2SpecMass    OBJECT-TYPE
    SYNTAX    Integer32
    UNITS    "0.1 kg"
    MAX-ACCESS    read-only
    STATUS    current
    DESCRIPTION    "This shows the weight of management module2."
    ::= { mm2InfoSpec 2 }

mm2SpecUpperLimitTemp    OBJECT-TYPE
    SYNTAX    Integer32
    UNITS    "0.1 degrees C"
    MAX-ACCESS    read-only
    STATUS    current
    DESCRIPTION    "This shows the maximum limied temperature of management module2."
    ::= { mm2InfoSpec 3 }

mm2SpecLowerLimitTemp    OBJECT-TYPE
    SYNTAX    Integer32
    UNITS    "0.1 degrees C"
    MAX-ACCESS    read-only
    STATUS    current
    DESCRIPTION    "This shows the minimum limied temperature of management module2."
    ::= { mm2InfoSpec 4 }

managementModule2Capacity    OBJECT IDENTIFIER ::= { managementModule2 2 } 

mm2CapacityVoltageSensor    OBJECT-TYPE
    SYNTAX    Integer32
    MAX-ACCESS    read-only
    STATUS    current
    DESCRIPTION    "This shows the capacity of voltage sensors of management module2."
    ::= { managementModule2Capacity 1 }

mm2CapacityTempSensor    OBJECT-TYPE
    SYNTAX    Integer32
    MAX-ACCESS    read-only
    STATUS    current
    DESCRIPTION    "This shows the capacity of temperature sensors of management module2."
    ::= { managementModule2Capacity 2 }

mm2CapacityLED    OBJECT-TYPE
    SYNTAX    Integer32
    MAX-ACCESS    read-only
    STATUS    current
    DESCRIPTION    "This shows the capacity of count of LEDs of management module2."
    ::= { managementModule2Capacity 3 }

managementModule2Settings    OBJECT IDENTIFIER ::= { managementModule2 3 } 

mm2SettingsManagementIPAddress    OBJECT-TYPE
    SYNTAX    DisplayString 
    MAX-ACCESS    read-only
    STATUS    current
    DESCRIPTION    "This shows the management LAN IP address of management module2."
    ::= { managementModule2Settings 1 }

mm2SettingsMaintIPAddress    OBJECT-TYPE
    SYNTAX    DisplayString 
    MAX-ACCESS    read-only
    STATUS    current
    DESCRIPTION    "This shows the maintenance LAN IP address of management module2."
    ::= { managementModule2Settings 2 }

managementModule2State    OBJECT IDENTIFIER ::= { managementModule2 4 } 

mm2StateSlotNum    OBJECT-TYPE
    SYNTAX    Integer32
    MAX-ACCESS    read-only
    STATUS    current
    DESCRIPTION    "This shows the number of installed slots of management module2."
    ::= { managementModule2State 1 }

mm2StatePower    OBJECT-TYPE
    SYNTAX    INTEGER {
    poweroff (1), standby (2), poweron (3), unknown (4),poweron-executing (5),poweroff-executing (6)
    }
    MAX-ACCESS    read-only
    STATUS    current
    DESCRIPTION    "This shows the power supply state of management module2."
    ::= { managementModule2State 2 }

mm2StateHealth    OBJECT-TYPE
    SYNTAX    INTEGER {
    normal (1),fail (2),unknown (3)
    }
    MAX-ACCESS    read-only
    STATUS    current
    DESCRIPTION    "This shows the health state of management module2."
    ::= { managementModule2State 3 }

mm2StateActive    OBJECT-TYPE
    SYNTAX    INTEGER {
    active(1), standby(2), unknown(3)
    }
    MAX-ACCESS    read-only
    STATUS    current
    DESCRIPTION    "This shows the operating mode of management module2."
    ::= { managementModule2State 4 }

mm2StateLEDTable    OBJECT-TYPE
    SYNTAX SEQUENCE OF mm2StateLEDEntry
    MAX-ACCESS not-accessible
    STATUS     current
    DESCRIPTION "This shows the table of LED of management module2."
    ::= { managementModule2State 5 }

mm2StateLEDEntry    OBJECT-TYPE
    SYNTAX Mm2StateLEDEntry
    MAX-ACCESS not-accessible
    STATUS    current
    DESCRIPTION "This shows the entry of LED of management module2."
    INDEX { mm2StateLEDIndex }
    ::= { mm2StateLEDTable 1 }

mm2StateLEDIndex    OBJECT-TYPE
    SYNTAX    Integer32
    MAX-ACCESS    read-only
    STATUS    current
    DESCRIPTION    "This shows the index of LED of management module2."
    ::= { mm2StateLEDEntry 1 }

mm2StateLEDName    OBJECT-TYPE
    SYNTAX    DisplayString (SIZE(0..40))
    MAX-ACCESS    read-only
    STATUS    current
    DESCRIPTION    "This shows the name of LED of management module2."
    ::= { mm2StateLEDEntry 2 }

mm2StateLEDState    OBJECT-TYPE
    SYNTAX    INTEGER {
    turn-off(1), turn-on(2),  unknown(3), blink(4), blink-fast(5), blink-slow(6)
    }
    MAX-ACCESS    read-only
    STATUS    current
    DESCRIPTION    "This shows the state of LED of management module2."
    ::= { mm2StateLEDEntry 3 }

mm2StateLEDColor    OBJECT-TYPE
    SYNTAX    INTEGER {
    blue (1),green (2),red (3),amber (4),unknown (5)
    }
    MAX-ACCESS    read-only
    STATUS    current
    DESCRIPTION    "This shows the color of LED of management module2."
    ::= { mm2StateLEDEntry 4 }

Mm2StateLEDEntry ::= SEQUENCE {
    mm2StateLEDIndex
        Integer32,
    mm2StateLEDName
        DisplayString,
    mm2StateLEDState
        INTEGER,
    mm2StateLEDColor
        INTEGER
}

mm2StateOther    OBJECT IDENTIFIER ::= { managementModule2State 20 } 

mm2MaintMode    OBJECT-TYPE
    SYNTAX    INTEGER {
    Normal(1), CE-Maint-mode(2), User-Maint-mode(3), unknown(4)
    }
    MAX-ACCESS    read-only
    STATUS    current
    DESCRIPTION    "This shows the maintenance mode of management module2."
    ::= { mm2StateOther 1 }

mm2VoltageSensorTable    OBJECT-TYPE
    SYNTAX SEQUENCE OF mm2VoltageSensorEntry
    MAX-ACCESS not-accessible
    STATUS     current
    DESCRIPTION "This shows the table of voltage sensor of management module2."
    ::= { managementModule2State 30 }

mm2VoltageSensorEntry    OBJECT-TYPE
    SYNTAX Mm2VoltageSensorEntry
    MAX-ACCESS not-accessible
    STATUS    current
    DESCRIPTION "This shows the entry of voltage sensor of management module2."
    INDEX { mm2VoltageSensorIndex }
    ::= { mm2VoltageSensorTable 1 }

mm2VoltageSensorIndex    OBJECT-TYPE
    SYNTAX    Integer32
    MAX-ACCESS    read-only
    STATUS    current
    DESCRIPTION    "This shows the index of voltage sensor of management module2."
    ::= { mm2VoltageSensorEntry 1 }

mm2VoltageSensorName    OBJECT-TYPE
    SYNTAX    DisplayString (SIZE(0..40))
    MAX-ACCESS    read-only
    STATUS    current
    DESCRIPTION    "This shows the voltage sensor name of management module2."
    ::= { mm2VoltageSensorEntry 2 }

mm2VoltageSensorValue    OBJECT-TYPE
    SYNTAX    Integer32
    UNITS    "0.1 V"
    MAX-ACCESS    read-only
    STATUS    current
    DESCRIPTION    "This shows the voltage sensor value of management module2."
    ::= { mm2VoltageSensorEntry 3 }

mm2VoltageSensorValid    OBJECT-TYPE
    SYNTAX    INTEGER {
    invalid (1),valid (2),unknown (3)
    }
    MAX-ACCESS    read-only
    STATUS    current
    DESCRIPTION    "This shows the validity of voltage sensor value of management module2."
    ::= { mm2VoltageSensorEntry 4 }

Mm2VoltageSensorEntry ::= SEQUENCE {
    mm2VoltageSensorIndex
        Integer32,
    mm2VoltageSensorName
        DisplayString,
    mm2VoltageSensorValue
        Integer32,
    mm2VoltageSensorValid
        INTEGER
}

mm2TempSensorTable    OBJECT-TYPE
    SYNTAX SEQUENCE OF mm2TempSensorEntry
    MAX-ACCESS not-accessible
    STATUS     current
    DESCRIPTION "This shows the table of temperature sensor of management module2."
    ::= { managementModule2State 31 }

mm2TempSensorEntry    OBJECT-TYPE
    SYNTAX Mm2TempSensorEntry
    MAX-ACCESS not-accessible
    STATUS    current
    DESCRIPTION "This shows the entry of temperature sensor of management module2."
    INDEX { mm2TempSensorIndex }
    ::= { mm2TempSensorTable 1 }

mm2TempSensorIndex    OBJECT-TYPE
    SYNTAX    Integer32
    MAX-ACCESS    read-only
    STATUS    current
    DESCRIPTION    "This shows the index of temperature sensor of management module2."
    ::= { mm2TempSensorEntry 1 }

mm2TempSensorName    OBJECT-TYPE
    SYNTAX    DisplayString (SIZE(0..40))
    MAX-ACCESS    read-only
    STATUS    current
    DESCRIPTION    "This shows the temperature sensor name of management module2."
    ::= { mm2TempSensorEntry 2 }

mm2TempSensorValue    OBJECT-TYPE
    SYNTAX    Integer32
    UNITS    "0.1 degrees C"
    MAX-ACCESS    read-only
    STATUS    current
    DESCRIPTION    "This shows the temperature sensor value of management module2."
    ::= { mm2TempSensorEntry 3 }

mm2TempSensorValid    OBJECT-TYPE
    SYNTAX    INTEGER {
    invalid (1),valid (2),unknown (3)
    }
    MAX-ACCESS    read-only
    STATUS    current
    DESCRIPTION    "This shows the validity of temperature sensor value of management module2."
    ::= { mm2TempSensorEntry 4 }

Mm2TempSensorEntry ::= SEQUENCE {
    mm2TempSensorIndex
        Integer32,
    mm2TempSensorName
        DisplayString,
    mm2TempSensorValue
        Integer32,
    mm2TempSensorValid
        INTEGER
}

managementModule2FWInfo    OBJECT IDENTIFIER ::= { managementModule2 5 } 

managementModule2FWInfoTotalVer    OBJECT-TYPE
    SYNTAX    DisplayString (SIZE(0..40))
    MAX-ACCESS    read-only
    STATUS    current
    DESCRIPTION    "This shows the total version of firmware of management module2."
    ::= { managementModule2FWInfo 1 }

managementModule2FWInfoTable    OBJECT-TYPE
    SYNTAX SEQUENCE OF managementModule2FWInfoEntry
    MAX-ACCESS not-accessible
    STATUS     current
    DESCRIPTION "This shows the table of firmware information of management module2."
    ::= { managementModule2FWInfo 2 }

managementModule2FWInfoEntry    OBJECT-TYPE
    SYNTAX ManagementModule2FWInfoEntry
    MAX-ACCESS not-accessible
    STATUS    current
    DESCRIPTION "This shows the entry of firmware information of management module2."
    INDEX { managementModule2FWInfoIndex }
    ::= { managementModule2FWInfoTable 1 }

managementModule2FWInfoIndex    OBJECT-TYPE
    SYNTAX    Integer32
    MAX-ACCESS    read-only
    STATUS    current
    DESCRIPTION    "This shows the index of firmware information of management module2."
    ::= { managementModule2FWInfoEntry 1 }

managementModule2FWInfoName    OBJECT-TYPE
    SYNTAX    DisplayString (SIZE(0..40))
    MAX-ACCESS    read-only
    STATUS    current
    DESCRIPTION    "This shows the firmware name of management module2."
    ::= { managementModule2FWInfoEntry 2 }

managementModule2FWInfoCurrentVer    OBJECT-TYPE
    SYNTAX    DisplayString (SIZE(0..40))
    MAX-ACCESS    read-only
    STATUS    current
    DESCRIPTION    "This shows the firmware current version of management module2."
    ::= { managementModule2FWInfoEntry 3 }

ManagementModule2FWInfoEntry ::= SEQUENCE {
    managementModule2FWInfoIndex
        Integer32,
    managementModule2FWInfoName
        DisplayString,
    managementModule2FWInfoCurrentVer
        DisplayString
}

switchModule    OBJECT IDENTIFIER ::= { component 3 } 

switchModule1    OBJECT IDENTIFIER ::= { switchModule 1 } 

switchModule1BasicInfo    OBJECT IDENTIFIER ::= { switchModule1 1 } 

sw1InfoProductName    OBJECT-TYPE
    SYNTAX    DisplayString (SIZE(0..40))
    MAX-ACCESS    read-only
    STATUS    current
    DESCRIPTION    "This shows the product name of switch module1."
    ::= { switchModule1BasicInfo 1 }

sw1InfoModel    OBJECT-TYPE
    SYNTAX    DisplayString (SIZE(0..40))
    MAX-ACCESS    read-only
    STATUS    current
    DESCRIPTION    "This shows the model name of switch module1."
    ::= { switchModule1BasicInfo 2 }

sw1InfoSerialNum    OBJECT-TYPE
    SYNTAX    DisplayString (SIZE(0..40))
    MAX-ACCESS    read-only
    STATUS    current
    DESCRIPTION    "This shows the serial number of switch module1."
    ::= { switchModule1BasicInfo 3 }

sw1InfoProductVersion    OBJECT-TYPE
    SYNTAX    DisplayString (SIZE(0..40))
    MAX-ACCESS    read-only
    STATUS    current
    DESCRIPTION    "This shows the product version of switch module1."
    ::= { switchModule1BasicInfo 4 }

sw1InfoProductManufacturer    OBJECT-TYPE
    SYNTAX    DisplayString (SIZE(0..40))
    MAX-ACCESS    read-only
    STATUS    current
    DESCRIPTION    "This shows the product manufacturer of switch module1."
    ::= { switchModule1BasicInfo 5 }

sw1InfoBoardProductName    OBJECT-TYPE
    SYNTAX    DisplayString (SIZE(0..40))
    MAX-ACCESS    read-only
    STATUS    current
    DESCRIPTION    "This shows the board product name of switch module1."
    ::= { switchModule1BasicInfo 6 }

sw1InfoBoardSerialNum    OBJECT-TYPE
    SYNTAX    DisplayString (SIZE(0..40))
    MAX-ACCESS    read-only
    STATUS    current
    DESCRIPTION    "This shows the board serial number of switch module1."
    ::= { switchModule1BasicInfo 7 }

sw1InfoBoardManufacturer    OBJECT-TYPE
    SYNTAX    DisplayString (SIZE(0..40))
    MAX-ACCESS    read-only
    STATUS    current
    DESCRIPTION    "This shows the board manufacutrer of switch module1."
    ::= { switchModule1BasicInfo 8 }

sw1InfoSpec    OBJECT IDENTIFIER ::= { switchModule1BasicInfo 20 } 

sw1SpecPowerConsumption    OBJECT-TYPE
    SYNTAX    Integer32
    UNITS    "W"
    MAX-ACCESS    read-only
    STATUS    current
    DESCRIPTION    "This shows the power consumption of switch module1."
    ::= { sw1InfoSpec 1 }

sw1SpecMass    OBJECT-TYPE
    SYNTAX    Integer32
    UNITS    "0.1 kg"
    MAX-ACCESS    read-only
    STATUS    current
    DESCRIPTION    "This shows the weight of switch module1."
    ::= { sw1InfoSpec 2 }

switchModule1Capacity    OBJECT IDENTIFIER ::= { switchModule1 2 } 

sw1CapacityLED    OBJECT-TYPE
    SYNTAX    Integer32
    MAX-ACCESS    read-only
    STATUS    current
    DESCRIPTION    "This shows the capacity of count of LEDs of switch module1."
    ::= { switchModule1Capacity 1 }

switchModule1State    OBJECT IDENTIFIER ::= { switchModule1 4 } 

sw1StateSlotNum    OBJECT-TYPE
    SYNTAX    Integer32
    MAX-ACCESS    read-only
    STATUS    current
    DESCRIPTION    "This shows the number of installed slot of switch module1."
    ::= { switchModule1State 1 }

sw1StatePower    OBJECT-TYPE
    SYNTAX    INTEGER {
    Poweroff(1), standby(2), PowerOn(3), unknown(4), Power-on-executing(5), Power-off-executing(6)
    }
    MAX-ACCESS    read-only
    STATUS    current
    DESCRIPTION    "This shows the power supply state of switch module1."
    ::= { switchModule1State 2 }

sw1StateHealth    OBJECT-TYPE
    SYNTAX    INTEGER {
    normal (1),fail (2),unknown (3)
    }
    MAX-ACCESS    read-only
    STATUS    current
    DESCRIPTION    "This shows the health state of switch module1."
    ::= { switchModule1State 3 }

sw1StateLEDTable    OBJECT-TYPE
    SYNTAX SEQUENCE OF sw1StateLEDEntry
    MAX-ACCESS not-accessible
    STATUS     current
    DESCRIPTION "This shows the table of LED of swich module1."
    ::= { switchModule1State 4 }

sw1StateLEDEntry    OBJECT-TYPE
    SYNTAX Sw1StateLEDEntry
    MAX-ACCESS not-accessible
    STATUS    current
    DESCRIPTION "This shows the entry of LED of swich module1."
    INDEX { sw1StateLEDIndex }
    ::= { sw1StateLEDTable 1 }

sw1StateLEDIndex    OBJECT-TYPE
    SYNTAX    Integer32
    MAX-ACCESS    read-only
    STATUS    current
    DESCRIPTION    "This shows the index of LED of swich module1."
    ::= { sw1StateLEDEntry 1 }

sw1StateLEDName    OBJECT-TYPE
    SYNTAX    DisplayString (SIZE(0..40))
    MAX-ACCESS    read-only
    STATUS    current
    DESCRIPTION    "This shows the name of LED of swich module1."
    ::= { sw1StateLEDEntry 2 }

sw1StateLEDState    OBJECT-TYPE
    SYNTAX    INTEGER {
    turn-off(1), turn-on(2),  unknown(3), blink(4), blink-fast(5), blink-slow(6)
    }
    MAX-ACCESS    read-only
    STATUS    current
    DESCRIPTION    "This shows the state of LED of swich module1."
    ::= { sw1StateLEDEntry 3 }

sw1StateLEDColor    OBJECT-TYPE
    SYNTAX    INTEGER {
    blue (1),green (2),red (3),amber (4),unknown (5)
    }
    MAX-ACCESS    read-only
    STATUS    current
    DESCRIPTION    "This shows the color of LED of swich module1."
    ::= { sw1StateLEDEntry 4 }

Sw1StateLEDEntry ::= SEQUENCE {
    sw1StateLEDIndex
        Integer32,
    sw1StateLEDName
        DisplayString,
    sw1StateLEDState
        INTEGER,
    sw1StateLEDColor
        INTEGER
}

sw1StateOther    OBJECT IDENTIFIER ::= { switchModule1State 20 } 

sw1MaintMode    OBJECT-TYPE
    SYNTAX    INTEGER {
    Normal(1), CE-Maint-mode(2), User-Maint-mode(3), unknown(4)
    }
    MAX-ACCESS    read-only
    STATUS    current
    DESCRIPTION    "This shows the maintenance mode of switch module1."
    ::= { sw1StateOther 1 }

sw1VoltageSensorTable    OBJECT-TYPE
    SYNTAX SEQUENCE OF sw1VoltageSensorEntry
    MAX-ACCESS not-accessible
    STATUS     current
    DESCRIPTION "This shows the table of voltage sensor of switch module1."
    ::= { switchModule1State 30 }

sw1VoltageSensorEntry    OBJECT-TYPE
    SYNTAX Sw1VoltageSensorEntry
    MAX-ACCESS not-accessible
    STATUS    current
    DESCRIPTION "This shows the entry of voltage sensor of switch module1."
    INDEX { sw1VoltageSensorIndex }
    ::= { sw1VoltageSensorTable 1 }

sw1VoltageSensorIndex    OBJECT-TYPE
    SYNTAX    Integer32
    MAX-ACCESS    read-only
    STATUS    current
    DESCRIPTION    "This shows the index of voltage sensor of switch module1."
    ::= { sw1VoltageSensorEntry 1 }

sw1VoltageSensorName    OBJECT-TYPE
    SYNTAX    DisplayString (SIZE(0..40))
    MAX-ACCESS    read-only
    STATUS    current
    DESCRIPTION    "This shows the voltage sensor name of switch module1."
    ::= { sw1VoltageSensorEntry 2 }

sw1VoltageSensorValue    OBJECT-TYPE
    SYNTAX    Integer32
    UNITS    "0.1 V"
    MAX-ACCESS    read-only
    STATUS    current
    DESCRIPTION    "This shows the voltage sensor value of switch module1."
    ::= { sw1VoltageSensorEntry 3 }

sw1VoltageSensorValid    OBJECT-TYPE
    SYNTAX    INTEGER {
    invalid (1),valid (2),unknown (3)
    }
    MAX-ACCESS    read-only
    STATUS    current
    DESCRIPTION    "This shows the validity of voltage sensor value of switch module1."
    ::= { sw1VoltageSensorEntry 4 }

Sw1VoltageSensorEntry ::= SEQUENCE {
    sw1VoltageSensorIndex
        Integer32,
    sw1VoltageSensorName
        DisplayString,
    sw1VoltageSensorValue
        Integer32,
    sw1VoltageSensorValid
        INTEGER
}

sw1TempSensorTable    OBJECT-TYPE
    SYNTAX SEQUENCE OF sw1TempSensorEntry
    MAX-ACCESS not-accessible
    STATUS     current
    DESCRIPTION "This shows the table of temperature sensor of switch module1."
    ::= { switchModule1State 31 }

sw1TempSensorEntry    OBJECT-TYPE
    SYNTAX Sw1TempSensorEntry
    MAX-ACCESS not-accessible
    STATUS    current
    DESCRIPTION "This shows the entry of temperature sensor of switch module1."
    INDEX { sw1TempSensorIndex }
    ::= { sw1TempSensorTable 1 }

sw1TempSensorIndex    OBJECT-TYPE
    SYNTAX    Integer32
    MAX-ACCESS    read-only
    STATUS    current
    DESCRIPTION    "This shows the index of temperature sensor of switch module1."
    ::= { sw1TempSensorEntry 1 }

sw1TempSensorName    OBJECT-TYPE
    SYNTAX    DisplayString (SIZE(0..40))
    MAX-ACCESS    read-only
    STATUS    current
    DESCRIPTION    "This shows the temerature sensor name of switch module1."
    ::= { sw1TempSensorEntry 2 }

sw1TempSensorValue    OBJECT-TYPE
    SYNTAX    Integer32
    UNITS    "0.1 degrees C"
    MAX-ACCESS    read-only
    STATUS    current
    DESCRIPTION    "This shows the temperature sensor value of switch module1."
    ::= { sw1TempSensorEntry 3 }

sw1TempSensorValid    OBJECT-TYPE
    SYNTAX    INTEGER {
    invalid (1),valid (2),unknown (3)
    }
    MAX-ACCESS    read-only
    STATUS    current
    DESCRIPTION    "This shows the validity of temperature sensor value of switch module1."
    ::= { sw1TempSensorEntry 4 }

Sw1TempSensorEntry ::= SEQUENCE {
    sw1TempSensorIndex
        Integer32,
    sw1TempSensorName
        DisplayString,
    sw1TempSensorValue
        Integer32,
    sw1TempSensorValid
        INTEGER
}

sw1CurrentSensorTable    OBJECT-TYPE
    SYNTAX SEQUENCE OF sw1CurrentSensorEntry
    MAX-ACCESS not-accessible
    STATUS     current
    DESCRIPTION "This shows the table of current sensor of switch module1."
    ::= { switchModule1State 32 }

sw1CurrentSensorEntry    OBJECT-TYPE
    SYNTAX Sw1CurrentSensorEntry
    MAX-ACCESS not-accessible
    STATUS    current
    DESCRIPTION "This shows the entry of current sensor of switch module1."
    INDEX { sw1CurrentSensorIndex }
    ::= { sw1CurrentSensorTable 1 }

sw1CurrentSensorIndex    OBJECT-TYPE
    SYNTAX    Integer32
    MAX-ACCESS    read-only
    STATUS    current
    DESCRIPTION    "This shows the index of current sensor of switch module1."
    ::= { sw1CurrentSensorEntry 1 }

sw1CurrentSensorName    OBJECT-TYPE
    SYNTAX    DisplayString (SIZE(0..40))
    MAX-ACCESS    read-only
    STATUS    current
    DESCRIPTION    "This shows the current sensor name of switch module1."
    ::= { sw1CurrentSensorEntry 2 }

sw1CurrentSensorValue    OBJECT-TYPE
    SYNTAX    Integer32
    UNITS    "0.1 A"
    MAX-ACCESS    read-only
    STATUS    current
    DESCRIPTION    "This shows the current sensor value of switch module1."
    ::= { sw1CurrentSensorEntry 3 }

sw1CurrentSensorValid    OBJECT-TYPE
    SYNTAX    INTEGER {
    invalid (1),valid (2),unknown (3)
    }
    MAX-ACCESS    read-only
    STATUS    current
    DESCRIPTION    "This shows the validity of current sensor value of switch module1."
    ::= { sw1CurrentSensorEntry 4 }

Sw1CurrentSensorEntry ::= SEQUENCE {
    sw1CurrentSensorIndex
        Integer32,
    sw1CurrentSensorName
        DisplayString,
    sw1CurrentSensorValue
        Integer32,
    sw1CurrentSensorValid
        INTEGER
}

switchModule1FWInfo    OBJECT IDENTIFIER ::= { switchModule1 5 } 

switchModule1FWInfoTotalVer    OBJECT-TYPE
    SYNTAX    DisplayString (SIZE(0..40))
    MAX-ACCESS    read-only
    STATUS    current
    DESCRIPTION    "This shows the total version of firmware of switch module1."
    ::= { switchModule1FWInfo 1 }

switchModule1FWInfoTable    OBJECT-TYPE
    SYNTAX SEQUENCE OF switchModule1FWInfoEntry
    MAX-ACCESS not-accessible
    STATUS     current
    DESCRIPTION "This shows the table of firmware information of switch module1."
    ::= { switchModule1FWInfo 2 }

switchModule1FWInfoEntry    OBJECT-TYPE
    SYNTAX SwitchModule1FWInfoEntry
    MAX-ACCESS not-accessible
    STATUS    current
    DESCRIPTION "This shows the entry of firmware information of switch module1."
    INDEX { switchModule1FWInfoIndex }
    ::= { switchModule1FWInfoTable 1 }

switchModule1FWInfoIndex    OBJECT-TYPE
    SYNTAX    Integer32
    MAX-ACCESS    read-only
    STATUS    current
    DESCRIPTION    "This shows the index of firmware information of switch module1."
    ::= { switchModule1FWInfoEntry 1 }

switchModule1FWInfoName    OBJECT-TYPE
    SYNTAX    DisplayString (SIZE(0..40))
    MAX-ACCESS    read-only
    STATUS    current
    DESCRIPTION    "This shows the firmware name of switch module1."
    ::= { switchModule1FWInfoEntry 2 }

switchModule1FWInfoCurrentVer    OBJECT-TYPE
    SYNTAX    DisplayString (SIZE(0..40))
    MAX-ACCESS    read-only
    STATUS    current
    DESCRIPTION    "This shows the firmware current version of switch module1."
    ::= { switchModule1FWInfoEntry 3 }

SwitchModule1FWInfoEntry ::= SEQUENCE {
    switchModule1FWInfoIndex
        Integer32,
    switchModule1FWInfoName
        DisplayString,
    switchModule1FWInfoCurrentVer
        DisplayString
}

switchModule2    OBJECT IDENTIFIER ::= { switchModule 2 } 

switchModule2BasicInfo    OBJECT IDENTIFIER ::= { switchModule2 1 } 

sw2InfoProductName    OBJECT-TYPE
    SYNTAX    DisplayString (SIZE(0..40))
    MAX-ACCESS    read-only
    STATUS    current
    DESCRIPTION    "This shows the product name of switch module2."
    ::= { switchModule2BasicInfo 1 }

sw2InfoModel    OBJECT-TYPE
    SYNTAX    DisplayString (SIZE(0..40))
    MAX-ACCESS    read-only
    STATUS    current
    DESCRIPTION    "This shows the model name of switch module2."
    ::= { switchModule2BasicInfo 2 }

sw2InfoSerialNum    OBJECT-TYPE
    SYNTAX    DisplayString (SIZE(0..40))
    MAX-ACCESS    read-only
    STATUS    current
    DESCRIPTION    "This shows the serial number of switch module2."
    ::= { switchModule2BasicInfo 3 }

sw2InfoProductVersion    OBJECT-TYPE
    SYNTAX    DisplayString (SIZE(0..40))
    MAX-ACCESS    read-only
    STATUS    current
    DESCRIPTION    "This shows the product version of switch module2."
    ::= { switchModule2BasicInfo 4 }

sw2InfoProductManufacturer    OBJECT-TYPE
    SYNTAX    DisplayString (SIZE(0..40))
    MAX-ACCESS    read-only
    STATUS    current
    DESCRIPTION    "This shows the product manufacturer of switch module2."
    ::= { switchModule2BasicInfo 5 }

sw2InfoBoardProductName    OBJECT-TYPE
    SYNTAX    DisplayString (SIZE(0..40))
    MAX-ACCESS    read-only
    STATUS    current
    DESCRIPTION    "This shows the board product name of switch module2."
    ::= { switchModule2BasicInfo 6 }

sw2InfoBoardSerialNum    OBJECT-TYPE
    SYNTAX    DisplayString (SIZE(0..40))
    MAX-ACCESS    read-only
    STATUS    current
    DESCRIPTION    "This shows the board serial number of switch module2."
    ::= { switchModule2BasicInfo 7 }

sw2InfoBoardManufacturer    OBJECT-TYPE
    SYNTAX    DisplayString (SIZE(0..40))
    MAX-ACCESS    read-only
    STATUS    current
    DESCRIPTION    "This shows the board manufacutrer of switch module2."
    ::= { switchModule2BasicInfo 8 }

sw2InfoSpec    OBJECT IDENTIFIER ::= { switchModule2BasicInfo 20 } 

sw2SpecPowerConsumption    OBJECT-TYPE
    SYNTAX    Integer32
    UNITS    "W"
    MAX-ACCESS    read-only
    STATUS    current
    DESCRIPTION    "This shows the power consumption of switch module2."
    ::= { sw2InfoSpec 1 }

sw2SpecMass    OBJECT-TYPE
    SYNTAX    Integer32
    UNITS    "0.1 kg"
    MAX-ACCESS    read-only
    STATUS    current
    DESCRIPTION    "This shows the weight of switch module2."
    ::= { sw2InfoSpec 2 }

switchModule2Capacity    OBJECT IDENTIFIER ::= { switchModule2 2 } 

sw2CapacityLED    OBJECT-TYPE
    SYNTAX    Integer32
    MAX-ACCESS    read-only
    STATUS    current
    DESCRIPTION    "This shows the capacity of count of LEDs of switch module2."
    ::= { switchModule2Capacity 1 }

switchModule2State    OBJECT IDENTIFIER ::= { switchModule2 4 } 

sw2StateSlotNum    OBJECT-TYPE
    SYNTAX    Integer32
    MAX-ACCESS    read-only
    STATUS    current
    DESCRIPTION    "This shows the number of installed slot of switch module2."
    ::= { switchModule2State 1 }

sw2StatePower    OBJECT-TYPE
    SYNTAX    INTEGER {
    Poweroff(1), standby(2), PowerOn(3), unknown(4), Power-on-executing(5), Power-off-executing(6)
    }
    MAX-ACCESS    read-only
    STATUS    current
    DESCRIPTION    "This shows the power supply state of switch module2."
    ::= { switchModule2State 2 }

sw2StateHealth    OBJECT-TYPE
    SYNTAX    INTEGER {
    normal (1),fail (2),unknown (3)
    }
    MAX-ACCESS    read-only
    STATUS    current
    DESCRIPTION    "This shows the health state of switch module2."
    ::= { switchModule2State 3 }

sw2StateLEDTable    OBJECT-TYPE
    SYNTAX SEQUENCE OF sw2StateLEDEntry
    MAX-ACCESS not-accessible
    STATUS     current
    DESCRIPTION "This shows the table of LED of swich module2."
    ::= { switchModule2State 4 }

sw2StateLEDEntry    OBJECT-TYPE
    SYNTAX Sw2StateLEDEntry
    MAX-ACCESS not-accessible
    STATUS    current
    DESCRIPTION "This shows the entry of LED of swich module2."
    INDEX { sw2StateLEDIndex }
    ::= { sw2StateLEDTable 1 }

sw2StateLEDIndex    OBJECT-TYPE
    SYNTAX    Integer32
    MAX-ACCESS    read-only
    STATUS    current
    DESCRIPTION    "This shows the index of LED of swich module2."
    ::= { sw2StateLEDEntry 1 }

sw2StateLEDName    OBJECT-TYPE
    SYNTAX    DisplayString (SIZE(0..40))
    MAX-ACCESS    read-only
    STATUS    current
    DESCRIPTION    "This shows the name of LED of swich module2."
    ::= { sw2StateLEDEntry 2 }

sw2StateLEDState    OBJECT-TYPE
    SYNTAX    INTEGER {
    turn-off(1), turn-on(2),  unknown(3), blink(4), blink-fast(5), blink-slow(6)
    }
    MAX-ACCESS    read-only
    STATUS    current
    DESCRIPTION    "This shows the state of LED of swich module2."
    ::= { sw2StateLEDEntry 3 }

sw2StateLEDColor    OBJECT-TYPE
    SYNTAX    INTEGER {
    blue (1),green (2),red (3),amber (4),unknown (5)
    }
    MAX-ACCESS    read-only
    STATUS    current
    DESCRIPTION    "This shows the color of LED of swich module2."
    ::= { sw2StateLEDEntry 4 }

Sw2StateLEDEntry ::= SEQUENCE {
    sw2StateLEDIndex
        Integer32,
    sw2StateLEDName
        DisplayString,
    sw2StateLEDState
        INTEGER,
    sw2StateLEDColor
        INTEGER
}

sw2StateOther    OBJECT IDENTIFIER ::= { switchModule2State 20 } 

sw2MaintMode    OBJECT-TYPE
    SYNTAX    INTEGER {
    Normal(1), CE-Maint-mode(2), User-Maint-mode(3), unknown(4)
    }
    MAX-ACCESS    read-only
    STATUS    current
    DESCRIPTION    "This shows the maintenance mode of switch module2."
    ::= { sw2StateOther 1 }

sw2VoltageSensorTable    OBJECT-TYPE
    SYNTAX SEQUENCE OF sw2VoltageSensorEntry
    MAX-ACCESS not-accessible
    STATUS     current
    DESCRIPTION "This shows the table of voltage sensor of switch module2."
    ::= { switchModule2State 30 }

sw2VoltageSensorEntry    OBJECT-TYPE
    SYNTAX Sw2VoltageSensorEntry
    MAX-ACCESS not-accessible
    STATUS    current
    DESCRIPTION "This shows the entry of voltage sensor of switch module2."
    INDEX { sw2VoltageSensorIndex }
    ::= { sw2VoltageSensorTable 1 }

sw2VoltageSensorIndex    OBJECT-TYPE
    SYNTAX    Integer32
    MAX-ACCESS    read-only
    STATUS    current
    DESCRIPTION    "This shows the index of voltage sensor of switch module2."
    ::= { sw2VoltageSensorEntry 1 }

sw2VoltageSensorName    OBJECT-TYPE
    SYNTAX    DisplayString (SIZE(0..40))
    MAX-ACCESS    read-only
    STATUS    current
    DESCRIPTION    "This shows the voltage sensor name of switch module2."
    ::= { sw2VoltageSensorEntry 2 }

sw2VoltageSensorValue    OBJECT-TYPE
    SYNTAX    Integer32
    UNITS    "0.1 V"
    MAX-ACCESS    read-only
    STATUS    current
    DESCRIPTION    "This shows the voltage sensor value of switch module2."
    ::= { sw2VoltageSensorEntry 3 }

sw2VoltageSensorValid    OBJECT-TYPE
    SYNTAX    INTEGER {
    invalid (1),valid (2),unknown (3)
    }
    MAX-ACCESS    read-only
    STATUS    current
    DESCRIPTION    "This shows the validity of voltage sensor value of switch module2."
    ::= { sw2VoltageSensorEntry 4 }

Sw2VoltageSensorEntry ::= SEQUENCE {
    sw2VoltageSensorIndex
        Integer32,
    sw2VoltageSensorName
        DisplayString,
    sw2VoltageSensorValue
        Integer32,
    sw2VoltageSensorValid
        INTEGER
}

sw2TempSensorTable    OBJECT-TYPE
    SYNTAX SEQUENCE OF sw2TempSensorEntry
    MAX-ACCESS not-accessible
    STATUS     current
    DESCRIPTION "This shows the table of temperature sensor of switch module2."
    ::= { switchModule2State 31 }

sw2TempSensorEntry    OBJECT-TYPE
    SYNTAX Sw2TempSensorEntry
    MAX-ACCESS not-accessible
    STATUS    current
    DESCRIPTION "This shows the entry of temperature sensor of switch module2."
    INDEX { sw2TempSensorIndex }
    ::= { sw2TempSensorTable 1 }

sw2TempSensorIndex    OBJECT-TYPE
    SYNTAX    Integer32
    MAX-ACCESS    read-only
    STATUS    current
    DESCRIPTION    "This shows the index of temperature sensor of switch module2."
    ::= { sw2TempSensorEntry 1 }

sw2TempSensorName    OBJECT-TYPE
    SYNTAX    DisplayString (SIZE(0..40))
    MAX-ACCESS    read-only
    STATUS    current
    DESCRIPTION    "This shows the temerature sensor name of switch module2."
    ::= { sw2TempSensorEntry 2 }

sw2TempSensorValue    OBJECT-TYPE
    SYNTAX    Integer32
    UNITS    "0.1 degrees C"
    MAX-ACCESS    read-only
    STATUS    current
    DESCRIPTION    "This shows the temperature sensor value of switch module2."
    ::= { sw2TempSensorEntry 3 }

sw2TempSensorValid    OBJECT-TYPE
    SYNTAX    INTEGER {
    invalid (1),valid (2),unknown (3)
    }
    MAX-ACCESS    read-only
    STATUS    current
    DESCRIPTION    "This shows the validity of temperature sensor value of switch module2."
    ::= { sw2TempSensorEntry 4 }

Sw2TempSensorEntry ::= SEQUENCE {
    sw2TempSensorIndex
        Integer32,
    sw2TempSensorName
        DisplayString,
    sw2TempSensorValue
        Integer32,
    sw2TempSensorValid
        INTEGER
}

sw2CurrentSensorTable    OBJECT-TYPE
    SYNTAX SEQUENCE OF sw2CurrentSensorEntry
    MAX-ACCESS not-accessible
    STATUS     current
    DESCRIPTION "This shows the table of current sensor of switch module2."
    ::= { switchModule2State 32 }

sw2CurrentSensorEntry    OBJECT-TYPE
    SYNTAX Sw2CurrentSensorEntry
    MAX-ACCESS not-accessible
    STATUS    current
    DESCRIPTION "This shows the entry of current sensor of switch module2."
    INDEX { sw2CurrentSensorIndex }
    ::= { sw2CurrentSensorTable 1 }

sw2CurrentSensorIndex    OBJECT-TYPE
    SYNTAX    Integer32
    MAX-ACCESS    read-only
    STATUS    current
    DESCRIPTION    "This shows the index of current sensor of switch module2."
    ::= { sw2CurrentSensorEntry 1 }

sw2CurrentSensorName    OBJECT-TYPE
    SYNTAX    DisplayString (SIZE(0..40))
    MAX-ACCESS    read-only
    STATUS    current
    DESCRIPTION    "This shows the current sensor name of switch module2."
    ::= { sw2CurrentSensorEntry 2 }

sw2CurrentSensorValue    OBJECT-TYPE
    SYNTAX    Integer32
    UNITS    "0.1 A"
    MAX-ACCESS    read-only
    STATUS    current
    DESCRIPTION    "This shows the current sensor value of switch module2."
    ::= { sw2CurrentSensorEntry 3 }

sw2CurrentSensorValid    OBJECT-TYPE
    SYNTAX    INTEGER {
    invalid (1),valid (2),unknown (3)
    }
    MAX-ACCESS    read-only
    STATUS    current
    DESCRIPTION    "This shows the validity of current sensor value of switch module2."
    ::= { sw2CurrentSensorEntry 4 }

Sw2CurrentSensorEntry ::= SEQUENCE {
    sw2CurrentSensorIndex
        Integer32,
    sw2CurrentSensorName
        DisplayString,
    sw2CurrentSensorValue
        Integer32,
    sw2CurrentSensorValid
        INTEGER
}

switchModule2FWInfo    OBJECT IDENTIFIER ::= { switchModule2 5 } 

switchModule2FWInfoTotalVer    OBJECT-TYPE
    SYNTAX    DisplayString (SIZE(0..40))
    MAX-ACCESS    read-only
    STATUS    current
    DESCRIPTION    "This shows the total version of firmware of switch module2."
    ::= { switchModule2FWInfo 1 }

switchModule2FWInfoTable    OBJECT-TYPE
    SYNTAX SEQUENCE OF switchModule2FWInfoEntry
    MAX-ACCESS not-accessible
    STATUS     current
    DESCRIPTION "This shows the table of firmware information of switch module2."
    ::= { switchModule2FWInfo 2 }

switchModule2FWInfoEntry    OBJECT-TYPE
    SYNTAX SwitchModule2FWInfoEntry
    MAX-ACCESS not-accessible
    STATUS    current
    DESCRIPTION "This shows the entry of firmware information of switch module2."
    INDEX { switchModule2FWInfoIndex }
    ::= { switchModule2FWInfoTable 1 }

switchModule2FWInfoIndex    OBJECT-TYPE
    SYNTAX    Integer32
    MAX-ACCESS    read-only
    STATUS    current
    DESCRIPTION    "This shows the index of firmware information of switch module2."
    ::= { switchModule2FWInfoEntry 1 }

switchModule2FWInfoName    OBJECT-TYPE
    SYNTAX    DisplayString (SIZE(0..40))
    MAX-ACCESS    read-only
    STATUS    current
    DESCRIPTION    "This shows the firmware name of switch module2."
    ::= { switchModule2FWInfoEntry 2 }

switchModule2FWInfoCurrentVer    OBJECT-TYPE
    SYNTAX    DisplayString (SIZE(0..40))
    MAX-ACCESS    read-only
    STATUS    current
    DESCRIPTION    "This shows the firmware current version of switch module2."
    ::= { switchModule2FWInfoEntry 3 }

SwitchModule2FWInfoEntry ::= SEQUENCE {
    switchModule2FWInfoIndex
        Integer32,
    switchModule2FWInfoName
        DisplayString,
    switchModule2FWInfoCurrentVer
        DisplayString
}

switchModule3    OBJECT IDENTIFIER ::= { switchModule 3 } 

switchModule3BasicInfo    OBJECT IDENTIFIER ::= { switchModule3 1 } 

sw3InfoProductName    OBJECT-TYPE
    SYNTAX    DisplayString (SIZE(0..40))
    MAX-ACCESS    read-only
    STATUS    current
    DESCRIPTION    "This shows the product name of switch module3."
    ::= { switchModule3BasicInfo 1 }

sw3InfoModel    OBJECT-TYPE
    SYNTAX    DisplayString (SIZE(0..40))
    MAX-ACCESS    read-only
    STATUS    current
    DESCRIPTION    "This shows the model name of switch module3."
    ::= { switchModule3BasicInfo 2 }

sw3InfoSerialNum    OBJECT-TYPE
    SYNTAX    DisplayString (SIZE(0..40))
    MAX-ACCESS    read-only
    STATUS    current
    DESCRIPTION    "This shows the serial number of switch module3."
    ::= { switchModule3BasicInfo 3 }

sw3InfoProductVersion    OBJECT-TYPE
    SYNTAX    DisplayString (SIZE(0..40))
    MAX-ACCESS    read-only
    STATUS    current
    DESCRIPTION    "This shows the product version of switch module3."
    ::= { switchModule3BasicInfo 4 }

sw3InfoProductManufacturer    OBJECT-TYPE
    SYNTAX    DisplayString (SIZE(0..40))
    MAX-ACCESS    read-only
    STATUS    current
    DESCRIPTION    "This shows the product manufacturer of switch module3."
    ::= { switchModule3BasicInfo 5 }

sw3InfoBoardProductName    OBJECT-TYPE
    SYNTAX    DisplayString (SIZE(0..40))
    MAX-ACCESS    read-only
    STATUS    current
    DESCRIPTION    "This shows the board product name of switch module3."
    ::= { switchModule3BasicInfo 6 }

sw3InfoBoardSerialNum    OBJECT-TYPE
    SYNTAX    DisplayString (SIZE(0..40))
    MAX-ACCESS    read-only
    STATUS    current
    DESCRIPTION    "This shows the board serial number of switch module3."
    ::= { switchModule3BasicInfo 7 }

sw3InfoBoardManufacturer    OBJECT-TYPE
    SYNTAX    DisplayString (SIZE(0..40))
    MAX-ACCESS    read-only
    STATUS    current
    DESCRIPTION    "This shows the board manufacutrer of switch module3."
    ::= { switchModule3BasicInfo 8 }

sw3InfoSpec    OBJECT IDENTIFIER ::= { switchModule3BasicInfo 20 } 

sw3SpecPowerConsumption    OBJECT-TYPE
    SYNTAX    Integer32
    UNITS    "W"
    MAX-ACCESS    read-only
    STATUS    current
    DESCRIPTION    "This shows the power consumption of switch module3."
    ::= { sw3InfoSpec 1 }

sw3SpecMass    OBJECT-TYPE
    SYNTAX    Integer32
    UNITS    "0.1 kg"
    MAX-ACCESS    read-only
    STATUS    current
    DESCRIPTION    "This shows the weight of switch module3."
    ::= { sw3InfoSpec 2 }

switchModule3Capacity    OBJECT IDENTIFIER ::= { switchModule3 2 } 

sw3CapacityLED    OBJECT-TYPE
    SYNTAX    Integer32
    MAX-ACCESS    read-only
    STATUS    current
    DESCRIPTION    "This shows the capacity of count of LEDs of switch module3."
    ::= { switchModule3Capacity 1 }

switchModule3State    OBJECT IDENTIFIER ::= { switchModule3 4 } 

sw3StateSlotNum    OBJECT-TYPE
    SYNTAX    Integer32
    MAX-ACCESS    read-only
    STATUS    current
    DESCRIPTION    "This shows the number of installed slot of switch module3."
    ::= { switchModule3State 1 }

sw3StatePower    OBJECT-TYPE
    SYNTAX    INTEGER {
    Poweroff(1), standby(2), PowerOn(3), unknown(4), Power-on-executing(5), Power-off-executing(6)
    }
    MAX-ACCESS    read-only
    STATUS    current
    DESCRIPTION    "This shows the power supply state of switch module3."
    ::= { switchModule3State 2 }

sw3StateHealth    OBJECT-TYPE
    SYNTAX    INTEGER {
    normal (1),fail (2),unknown (3)
    }
    MAX-ACCESS    read-only
    STATUS    current
    DESCRIPTION    "This shows the health state of switch module3."
    ::= { switchModule3State 3 }

sw3StateLEDTable    OBJECT-TYPE
    SYNTAX SEQUENCE OF sw3StateLEDEntry
    MAX-ACCESS not-accessible
    STATUS     current
    DESCRIPTION "This shows the table of LED of swich module3."
    ::= { switchModule3State 4 }

sw3StateLEDEntry    OBJECT-TYPE
    SYNTAX Sw3StateLEDEntry
    MAX-ACCESS not-accessible
    STATUS    current
    DESCRIPTION "This shows the entry of LED of swich module3."
    INDEX { sw3StateLEDIndex }
    ::= { sw3StateLEDTable 1 }

sw3StateLEDIndex    OBJECT-TYPE
    SYNTAX    Integer32
    MAX-ACCESS    read-only
    STATUS    current
    DESCRIPTION    "This shows the index of LED of swich module3."
    ::= { sw3StateLEDEntry 1 }

sw3StateLEDName    OBJECT-TYPE
    SYNTAX    DisplayString (SIZE(0..40))
    MAX-ACCESS    read-only
    STATUS    current
    DESCRIPTION    "This shows the name of LED of swich module3."
    ::= { sw3StateLEDEntry 2 }

sw3StateLEDState    OBJECT-TYPE
    SYNTAX    INTEGER {
    turn-off(1), turn-on(2),  unknown(3), blink(4), blink-fast(5), blink-slow(6)
    }
    MAX-ACCESS    read-only
    STATUS    current
    DESCRIPTION    "This shows the state of LED of swich module3."
    ::= { sw3StateLEDEntry 3 }

sw3StateLEDColor    OBJECT-TYPE
    SYNTAX    INTEGER {
    blue (1),green (2),red (3),amber (4),unknown (5)
    }
    MAX-ACCESS    read-only
    STATUS    current
    DESCRIPTION    "This shows the color of LED of swich module3."
    ::= { sw3StateLEDEntry 4 }

Sw3StateLEDEntry ::= SEQUENCE {
    sw3StateLEDIndex
        Integer32,
    sw3StateLEDName
        DisplayString,
    sw3StateLEDState
        INTEGER,
    sw3StateLEDColor
        INTEGER
}

sw3StateOther    OBJECT IDENTIFIER ::= { switchModule3State 20 } 

sw3MaintMode    OBJECT-TYPE
    SYNTAX    INTEGER {
    Normal(1), CE-Maint-mode(2), User-Maint-mode(3), unknown(4)
    }
    MAX-ACCESS    read-only
    STATUS    current
    DESCRIPTION    "This shows the maintenance mode of switch module3."
    ::= { sw3StateOther 1 }

sw3VoltageSensorTable    OBJECT-TYPE
    SYNTAX SEQUENCE OF sw3VoltageSensorEntry
    MAX-ACCESS not-accessible
    STATUS     current
    DESCRIPTION "This shows the table of voltage sensor of switch module3."
    ::= { switchModule3State 30 }

sw3VoltageSensorEntry    OBJECT-TYPE
    SYNTAX Sw3VoltageSensorEntry
    MAX-ACCESS not-accessible
    STATUS    current
    DESCRIPTION "This shows the entry of voltage sensor of switch module3."
    INDEX { sw3VoltageSensorIndex }
    ::= { sw3VoltageSensorTable 1 }

sw3VoltageSensorIndex    OBJECT-TYPE
    SYNTAX    Integer32
    MAX-ACCESS    read-only
    STATUS    current
    DESCRIPTION    "This shows the index of voltage sensor of switch module3."
    ::= { sw3VoltageSensorEntry 1 }

sw3VoltageSensorName    OBJECT-TYPE
    SYNTAX    DisplayString (SIZE(0..40))
    MAX-ACCESS    read-only
    STATUS    current
    DESCRIPTION    "This shows the voltage sensor name of switch module3."
    ::= { sw3VoltageSensorEntry 2 }

sw3VoltageSensorValue    OBJECT-TYPE
    SYNTAX    Integer32
    UNITS    "0.1 V"
    MAX-ACCESS    read-only
    STATUS    current
    DESCRIPTION    "This shows the voltage sensor value of switch module3."
    ::= { sw3VoltageSensorEntry 3 }

sw3VoltageSensorValid    OBJECT-TYPE
    SYNTAX    INTEGER {
    invalid (1),valid (2),unknown (3)
    }
    MAX-ACCESS    read-only
    STATUS    current
    DESCRIPTION    "This shows the validity of voltage sensor value of switch module3."
    ::= { sw3VoltageSensorEntry 4 }

Sw3VoltageSensorEntry ::= SEQUENCE {
    sw3VoltageSensorIndex
        Integer32,
    sw3VoltageSensorName
        DisplayString,
    sw3VoltageSensorValue
        Integer32,
    sw3VoltageSensorValid
        INTEGER
}

sw3TempSensorTable    OBJECT-TYPE
    SYNTAX SEQUENCE OF sw3TempSensorEntry
    MAX-ACCESS not-accessible
    STATUS     current
    DESCRIPTION "This shows the table of temperature sensor of switch module3."
    ::= { switchModule3State 31 }

sw3TempSensorEntry    OBJECT-TYPE
    SYNTAX Sw3TempSensorEntry
    MAX-ACCESS not-accessible
    STATUS    current
    DESCRIPTION "This shows the entry of temperature sensor of switch module3."
    INDEX { sw3TempSensorIndex }
    ::= { sw3TempSensorTable 1 }

sw3TempSensorIndex    OBJECT-TYPE
    SYNTAX    Integer32
    MAX-ACCESS    read-only
    STATUS    current
    DESCRIPTION    "This shows the index of temperature sensor of switch module3."
    ::= { sw3TempSensorEntry 1 }

sw3TempSensorName    OBJECT-TYPE
    SYNTAX    DisplayString (SIZE(0..40))
    MAX-ACCESS    read-only
    STATUS    current
    DESCRIPTION    "This shows the temerature sensor name of switch module3."
    ::= { sw3TempSensorEntry 2 }

sw3TempSensorValue    OBJECT-TYPE
    SYNTAX    Integer32
    UNITS    "0.1 degrees C"
    MAX-ACCESS    read-only
    STATUS    current
    DESCRIPTION    "This shows the temperature sensor value of switch module3."
    ::= { sw3TempSensorEntry 3 }

sw3TempSensorValid    OBJECT-TYPE
    SYNTAX    INTEGER {
    invalid (1),valid (2),unknown (3)
    }
    MAX-ACCESS    read-only
    STATUS    current
    DESCRIPTION    "This shows the validity of temperature sensor value of switch module3."
    ::= { sw3TempSensorEntry 4 }

Sw3TempSensorEntry ::= SEQUENCE {
    sw3TempSensorIndex
        Integer32,
    sw3TempSensorName
        DisplayString,
    sw3TempSensorValue
        Integer32,
    sw3TempSensorValid
        INTEGER
}

sw3CurrentSensorTable    OBJECT-TYPE
    SYNTAX SEQUENCE OF sw3CurrentSensorEntry
    MAX-ACCESS not-accessible
    STATUS     current
    DESCRIPTION "This shows the table of current sensor of switch module3."
    ::= { switchModule3State 32 }

sw3CurrentSensorEntry    OBJECT-TYPE
    SYNTAX Sw3CurrentSensorEntry
    MAX-ACCESS not-accessible
    STATUS    current
    DESCRIPTION "This shows the entry of current sensor of switch module3."
    INDEX { sw3CurrentSensorIndex }
    ::= { sw3CurrentSensorTable 1 }

sw3CurrentSensorIndex    OBJECT-TYPE
    SYNTAX    Integer32
    MAX-ACCESS    read-only
    STATUS    current
    DESCRIPTION    "This shows the index of current sensor of switch module3."
    ::= { sw3CurrentSensorEntry 1 }

sw3CurrentSensorName    OBJECT-TYPE
    SYNTAX    DisplayString (SIZE(0..40))
    MAX-ACCESS    read-only
    STATUS    current
    DESCRIPTION    "This shows the current sensor name of switch module3."
    ::= { sw3CurrentSensorEntry 2 }

sw3CurrentSensorValue    OBJECT-TYPE
    SYNTAX    Integer32
    UNITS    "0.1 A"
    MAX-ACCESS    read-only
    STATUS    current
    DESCRIPTION    "This shows the current sensor value of switch module3."
    ::= { sw3CurrentSensorEntry 3 }

sw3CurrentSensorValid    OBJECT-TYPE
    SYNTAX    INTEGER {
    invalid (1),valid (2),unknown (3)
    }
    MAX-ACCESS    read-only
    STATUS    current
    DESCRIPTION    "This shows the validity of current sensor value of switch module3."
    ::= { sw3CurrentSensorEntry 4 }

Sw3CurrentSensorEntry ::= SEQUENCE {
    sw3CurrentSensorIndex
        Integer32,
    sw3CurrentSensorName
        DisplayString,
    sw3CurrentSensorValue
        Integer32,
    sw3CurrentSensorValid
        INTEGER
}

switchModule3FWInfo    OBJECT IDENTIFIER ::= { switchModule3 5 } 

switchModule3FWInfoTotalVer    OBJECT-TYPE
    SYNTAX    DisplayString (SIZE(0..40))
    MAX-ACCESS    read-only
    STATUS    current
    DESCRIPTION    "This shows the total version of firmware of switch module3."
    ::= { switchModule3FWInfo 1 }

switchModule3FWInfoTable    OBJECT-TYPE
    SYNTAX SEQUENCE OF switchModule3FWInfoEntry
    MAX-ACCESS not-accessible
    STATUS     current
    DESCRIPTION "This shows the table of firmware information of switch module3."
    ::= { switchModule3FWInfo 2 }

switchModule3FWInfoEntry    OBJECT-TYPE
    SYNTAX SwitchModule3FWInfoEntry
    MAX-ACCESS not-accessible
    STATUS    current
    DESCRIPTION "This shows the entry of firmware information of switch module3."
    INDEX { switchModule3FWInfoIndex }
    ::= { switchModule3FWInfoTable 1 }

switchModule3FWInfoIndex    OBJECT-TYPE
    SYNTAX    Integer32
    MAX-ACCESS    read-only
    STATUS    current
    DESCRIPTION    "This shows the index of firmware information of switch module3."
    ::= { switchModule3FWInfoEntry 1 }

switchModule3FWInfoName    OBJECT-TYPE
    SYNTAX    DisplayString (SIZE(0..40))
    MAX-ACCESS    read-only
    STATUS    current
    DESCRIPTION    "This shows the firmware name of switch module3."
    ::= { switchModule3FWInfoEntry 2 }

switchModule3FWInfoCurrentVer    OBJECT-TYPE
    SYNTAX    DisplayString (SIZE(0..40))
    MAX-ACCESS    read-only
    STATUS    current
    DESCRIPTION    "This shows the firmware current version of switch module3."
    ::= { switchModule3FWInfoEntry 3 }

SwitchModule3FWInfoEntry ::= SEQUENCE {
    switchModule3FWInfoIndex
        Integer32,
    switchModule3FWInfoName
        DisplayString,
    switchModule3FWInfoCurrentVer
        DisplayString
}

switchModule4    OBJECT IDENTIFIER ::= { switchModule 4 } 

switchModule4BasicInfo    OBJECT IDENTIFIER ::= { switchModule4 1 } 

sw4InfoProductName    OBJECT-TYPE
    SYNTAX    DisplayString (SIZE(0..40))
    MAX-ACCESS    read-only
    STATUS    current
    DESCRIPTION    "This shows the product name of switch module4."
    ::= { switchModule4BasicInfo 1 }

sw4InfoModel    OBJECT-TYPE
    SYNTAX    DisplayString (SIZE(0..40))
    MAX-ACCESS    read-only
    STATUS    current
    DESCRIPTION    "This shows the model name of switch module4."
    ::= { switchModule4BasicInfo 2 }

sw4InfoSerialNum    OBJECT-TYPE
    SYNTAX    DisplayString (SIZE(0..40))
    MAX-ACCESS    read-only
    STATUS    current
    DESCRIPTION    "This shows the serial number of switch module4."
    ::= { switchModule4BasicInfo 3 }

sw4InfoProductVersion    OBJECT-TYPE
    SYNTAX    DisplayString (SIZE(0..40))
    MAX-ACCESS    read-only
    STATUS    current
    DESCRIPTION    "This shows the product version of switch module4."
    ::= { switchModule4BasicInfo 4 }

sw4InfoProductManufacturer    OBJECT-TYPE
    SYNTAX    DisplayString (SIZE(0..40))
    MAX-ACCESS    read-only
    STATUS    current
    DESCRIPTION    "This shows the product manufacturer of switch module4."
    ::= { switchModule4BasicInfo 5 }

sw4InfoBoardProductName    OBJECT-TYPE
    SYNTAX    DisplayString (SIZE(0..40))
    MAX-ACCESS    read-only
    STATUS    current
    DESCRIPTION    "This shows the board product name of switch module4."
    ::= { switchModule4BasicInfo 6 }

sw4InfoBoardSerialNum    OBJECT-TYPE
    SYNTAX    DisplayString (SIZE(0..40))
    MAX-ACCESS    read-only
    STATUS    current
    DESCRIPTION    "This shows the board serial number of switch module4."
    ::= { switchModule4BasicInfo 7 }

sw4InfoBoardManufacturer    OBJECT-TYPE
    SYNTAX    DisplayString (SIZE(0..40))
    MAX-ACCESS    read-only
    STATUS    current
    DESCRIPTION    "This shows the board manufacutrer of switch module4."
    ::= { switchModule4BasicInfo 8 }

sw4InfoSpec    OBJECT IDENTIFIER ::= { switchModule4BasicInfo 20 } 

sw4SpecPowerConsumption    OBJECT-TYPE
    SYNTAX    Integer32
    UNITS    "W"
    MAX-ACCESS    read-only
    STATUS    current
    DESCRIPTION    "This shows the power consumption of switch module4."
    ::= { sw4InfoSpec 1 }

sw4SpecMass    OBJECT-TYPE
    SYNTAX    Integer32
    UNITS    "0.1 kg"
    MAX-ACCESS    read-only
    STATUS    current
    DESCRIPTION    "This shows the weight of switch module4."
    ::= { sw4InfoSpec 2 }

switchModule4Capacity    OBJECT IDENTIFIER ::= { switchModule4 2 } 

sw4CapacityLED    OBJECT-TYPE
    SYNTAX    Integer32
    MAX-ACCESS    read-only
    STATUS    current
    DESCRIPTION    "This shows the capacity of count of LEDs of switch module4."
    ::= { switchModule4Capacity 1 }

switchModule4State    OBJECT IDENTIFIER ::= { switchModule4 4 } 

sw4StateSlotNum    OBJECT-TYPE
    SYNTAX    Integer32
    MAX-ACCESS    read-only
    STATUS    current
    DESCRIPTION    "This shows the number of installed slot of switch module4."
    ::= { switchModule4State 1 }

sw4StatePower    OBJECT-TYPE
    SYNTAX    INTEGER {
    Poweroff(1), standby(2), PowerOn(3), unknown(4), Power-on-executing(5), Power-off-executing(6)
    }
    MAX-ACCESS    read-only
    STATUS    current
    DESCRIPTION    "This shows the power supply state of switch module4."
    ::= { switchModule4State 2 }

sw4StateHealth    OBJECT-TYPE
    SYNTAX    INTEGER {
    normal (1),fail (2),unknown (3)
    }
    MAX-ACCESS    read-only
    STATUS    current
    DESCRIPTION    "This shows the health state of switch module4."
    ::= { switchModule4State 3 }

sw4StateLEDTable    OBJECT-TYPE
    SYNTAX SEQUENCE OF sw4StateLEDEntry
    MAX-ACCESS not-accessible
    STATUS     current
    DESCRIPTION "This shows the table of LED of swich module4."
    ::= { switchModule4State 4 }

sw4StateLEDEntry    OBJECT-TYPE
    SYNTAX Sw4StateLEDEntry
    MAX-ACCESS not-accessible
    STATUS    current
    DESCRIPTION "This shows the entry of LED of swich module4."
    INDEX { sw4StateLEDIndex }
    ::= { sw4StateLEDTable 1 }

sw4StateLEDIndex    OBJECT-TYPE
    SYNTAX    Integer32
    MAX-ACCESS    read-only
    STATUS    current
    DESCRIPTION    "This shows the index of LED of swich module4."
    ::= { sw4StateLEDEntry 1 }

sw4StateLEDName    OBJECT-TYPE
    SYNTAX    DisplayString (SIZE(0..40))
    MAX-ACCESS    read-only
    STATUS    current
    DESCRIPTION    "This shows the name of LED of swich module4."
    ::= { sw4StateLEDEntry 2 }

sw4StateLEDState    OBJECT-TYPE
    SYNTAX    INTEGER {
    turn-off(1), turn-on(2),  unknown(3), blink(4), blink-fast(5), blink-slow(6)
    }
    MAX-ACCESS    read-only
    STATUS    current
    DESCRIPTION    "This shows the state of LED of swich module4."
    ::= { sw4StateLEDEntry 3 }

sw4StateLEDColor    OBJECT-TYPE
    SYNTAX    INTEGER {
    blue (1),green (2),red (3),amber (4),unknown (5)
    }
    MAX-ACCESS    read-only
    STATUS    current
    DESCRIPTION    "This shows the color of LED of swich module4."
    ::= { sw4StateLEDEntry 4 }

Sw4StateLEDEntry ::= SEQUENCE {
    sw4StateLEDIndex
        Integer32,
    sw4StateLEDName
        DisplayString,
    sw4StateLEDState
        INTEGER,
    sw4StateLEDColor
        INTEGER
}

sw4StateOther    OBJECT IDENTIFIER ::= { switchModule4State 20 } 

sw4MaintMode    OBJECT-TYPE
    SYNTAX    INTEGER {
    Normal(1), CE-Maint-mode(2), User-Maint-mode(3), unknown(4)
    }
    MAX-ACCESS    read-only
    STATUS    current
    DESCRIPTION    "This shows the maintenance mode of switch module4."
    ::= { sw4StateOther 1 }

sw4VoltageSensorTable    OBJECT-TYPE
    SYNTAX SEQUENCE OF sw4VoltageSensorEntry
    MAX-ACCESS not-accessible
    STATUS     current
    DESCRIPTION "This shows the table of voltage sensor of switch module4."
    ::= { switchModule4State 30 }

sw4VoltageSensorEntry    OBJECT-TYPE
    SYNTAX Sw4VoltageSensorEntry
    MAX-ACCESS not-accessible
    STATUS    current
    DESCRIPTION "This shows the entry of voltage sensor of switch module4."
    INDEX { sw4VoltageSensorIndex }
    ::= { sw4VoltageSensorTable 1 }

sw4VoltageSensorIndex    OBJECT-TYPE
    SYNTAX    Integer32
    MAX-ACCESS    read-only
    STATUS    current
    DESCRIPTION    "This shows the index of voltage sensor of switch module4."
    ::= { sw4VoltageSensorEntry 1 }

sw4VoltageSensorName    OBJECT-TYPE
    SYNTAX    DisplayString (SIZE(0..40))
    MAX-ACCESS    read-only
    STATUS    current
    DESCRIPTION    "This shows the voltage sensor name of switch module4."
    ::= { sw4VoltageSensorEntry 2 }

sw4VoltageSensorValue    OBJECT-TYPE
    SYNTAX    Integer32
    UNITS    "0.1 V"
    MAX-ACCESS    read-only
    STATUS    current
    DESCRIPTION    "This shows the voltage sensor value of switch module4."
    ::= { sw4VoltageSensorEntry 3 }

sw4VoltageSensorValid    OBJECT-TYPE
    SYNTAX    INTEGER {
    invalid (1),valid (2),unknown (3)
    }
    MAX-ACCESS    read-only
    STATUS    current
    DESCRIPTION    "This shows the validity of voltage sensor value of switch module4."
    ::= { sw4VoltageSensorEntry 4 }

Sw4VoltageSensorEntry ::= SEQUENCE {
    sw4VoltageSensorIndex
        Integer32,
    sw4VoltageSensorName
        DisplayString,
    sw4VoltageSensorValue
        Integer32,
    sw4VoltageSensorValid
        INTEGER
}

sw4TempSensorTable    OBJECT-TYPE
    SYNTAX SEQUENCE OF sw4TempSensorEntry
    MAX-ACCESS not-accessible
    STATUS     current
    DESCRIPTION "This shows the table of temperature sensor of switch module4."
    ::= { switchModule4State 31 }

sw4TempSensorEntry    OBJECT-TYPE
    SYNTAX Sw4TempSensorEntry
    MAX-ACCESS not-accessible
    STATUS    current
    DESCRIPTION "This shows the entry of temperature sensor of switch module4."
    INDEX { sw4TempSensorIndex }
    ::= { sw4TempSensorTable 1 }

sw4TempSensorIndex    OBJECT-TYPE
    SYNTAX    Integer32
    MAX-ACCESS    read-only
    STATUS    current
    DESCRIPTION    "This shows the index of temperature sensor of switch module4."
    ::= { sw4TempSensorEntry 1 }

sw4TempSensorName    OBJECT-TYPE
    SYNTAX    DisplayString (SIZE(0..40))
    MAX-ACCESS    read-only
    STATUS    current
    DESCRIPTION    "This shows the temerature sensor name of switch module4."
    ::= { sw4TempSensorEntry 2 }

sw4TempSensorValue    OBJECT-TYPE
    SYNTAX    Integer32
    UNITS    "0.1 degrees C"
    MAX-ACCESS    read-only
    STATUS    current
    DESCRIPTION    "This shows the temperature sensor value of switch module4."
    ::= { sw4TempSensorEntry 3 }

sw4TempSensorValid    OBJECT-TYPE
    SYNTAX    INTEGER {
    invalid (1),valid (2),unknown (3)
    }
    MAX-ACCESS    read-only
    STATUS    current
    DESCRIPTION    "This shows the validity of temperature sensor value of switch module4."
    ::= { sw4TempSensorEntry 4 }

Sw4TempSensorEntry ::= SEQUENCE {
    sw4TempSensorIndex
        Integer32,
    sw4TempSensorName
        DisplayString,
    sw4TempSensorValue
        Integer32,
    sw4TempSensorValid
        INTEGER
}

sw4CurrentSensorTable    OBJECT-TYPE
    SYNTAX SEQUENCE OF sw4CurrentSensorEntry
    MAX-ACCESS not-accessible
    STATUS     current
    DESCRIPTION "This shows the table of current sensor of switch module4."
    ::= { switchModule4State 32 }

sw4CurrentSensorEntry    OBJECT-TYPE
    SYNTAX Sw4CurrentSensorEntry
    MAX-ACCESS not-accessible
    STATUS    current
    DESCRIPTION "This shows the entry of current sensor of switch module4."
    INDEX { sw4CurrentSensorIndex }
    ::= { sw4CurrentSensorTable 1 }

sw4CurrentSensorIndex    OBJECT-TYPE
    SYNTAX    Integer32
    MAX-ACCESS    read-only
    STATUS    current
    DESCRIPTION    "This shows the index of current sensor of switch module4."
    ::= { sw4CurrentSensorEntry 1 }

sw4CurrentSensorName    OBJECT-TYPE
    SYNTAX    DisplayString (SIZE(0..40))
    MAX-ACCESS    read-only
    STATUS    current
    DESCRIPTION    "This shows the current sensor name of switch module4."
    ::= { sw4CurrentSensorEntry 2 }

sw4CurrentSensorValue    OBJECT-TYPE
    SYNTAX    Integer32
    UNITS    "0.1 A"
    MAX-ACCESS    read-only
    STATUS    current
    DESCRIPTION    "This shows the current sensor value of switch module4."
    ::= { sw4CurrentSensorEntry 3 }

sw4CurrentSensorValid    OBJECT-TYPE
    SYNTAX    INTEGER {
    invalid (1),valid (2),unknown (3)
    }
    MAX-ACCESS    read-only
    STATUS    current
    DESCRIPTION    "This shows the validity of current sensor value of switch module4."
    ::= { sw4CurrentSensorEntry 4 }

Sw4CurrentSensorEntry ::= SEQUENCE {
    sw4CurrentSensorIndex
        Integer32,
    sw4CurrentSensorName
        DisplayString,
    sw4CurrentSensorValue
        Integer32,
    sw4CurrentSensorValid
        INTEGER
}

switchModule4FWInfo    OBJECT IDENTIFIER ::= { switchModule4 5 } 

switchModule4FWInfoTotalVer    OBJECT-TYPE
    SYNTAX    DisplayString (SIZE(0..40))
    MAX-ACCESS    read-only
    STATUS    current
    DESCRIPTION    "This shows the total version of firmware of switch module4."
    ::= { switchModule4FWInfo 1 }

switchModule4FWInfoTable    OBJECT-TYPE
    SYNTAX SEQUENCE OF switchModule4FWInfoEntry
    MAX-ACCESS not-accessible
    STATUS     current
    DESCRIPTION "This shows the table of firmware information of switch module4."
    ::= { switchModule4FWInfo 2 }

switchModule4FWInfoEntry    OBJECT-TYPE
    SYNTAX SwitchModule4FWInfoEntry
    MAX-ACCESS not-accessible
    STATUS    current
    DESCRIPTION "This shows the entry of firmware information of switch module4."
    INDEX { switchModule4FWInfoIndex }
    ::= { switchModule4FWInfoTable 1 }

switchModule4FWInfoIndex    OBJECT-TYPE
    SYNTAX    Integer32
    MAX-ACCESS    read-only
    STATUS    current
    DESCRIPTION    "This shows the index of firmware information of switch module4."
    ::= { switchModule4FWInfoEntry 1 }

switchModule4FWInfoName    OBJECT-TYPE
    SYNTAX    DisplayString (SIZE(0..40))
    MAX-ACCESS    read-only
    STATUS    current
    DESCRIPTION    "This shows the firmware name of switch module4."
    ::= { switchModule4FWInfoEntry 2 }

switchModule4FWInfoCurrentVer    OBJECT-TYPE
    SYNTAX    DisplayString (SIZE(0..40))
    MAX-ACCESS    read-only
    STATUS    current
    DESCRIPTION    "This shows the firmware current version of switch module4."
    ::= { switchModule4FWInfoEntry 3 }

SwitchModule4FWInfoEntry ::= SEQUENCE {
    switchModule4FWInfoIndex
        Integer32,
    switchModule4FWInfoName
        DisplayString,
    switchModule4FWInfoCurrentVer
        DisplayString
}

fanModule    OBJECT IDENTIFIER ::= { component 4 } 

fanModule1    OBJECT IDENTIFIER ::= { fanModule 1 } 

fanModule1BasicInfo    OBJECT IDENTIFIER ::= { fanModule1 1 } 

fanModule1InfoType    OBJECT-TYPE
    SYNTAX    INTEGER
    MAX-ACCESS    read-only
    STATUS    current
    DESCRIPTION    "This shows the type of fan module1."
    ::= { fanModule1BasicInfo 1 }

fanModule1InfoSpec    OBJECT IDENTIFIER ::= { fanModule1BasicInfo 20 } 

fanModule1SpecPowerConsumption    OBJECT-TYPE
    SYNTAX    Integer32
    UNITS    "W"
    MAX-ACCESS    read-only
    STATUS    current
    DESCRIPTION    "This shows the power consumption of fan module1."
    ::= { fanModule1InfoSpec 1 }

fanModule1SpecMass    OBJECT-TYPE
    SYNTAX    Integer32
    UNITS    "0.1 kg"
    MAX-ACCESS    read-only
    STATUS    current
    DESCRIPTION    "This shows the weight of fan module1."
    ::= { fanModule1InfoSpec 2 }

fanModule1SpecMaxRPM    OBJECT-TYPE
    SYNTAX    Integer32
    UNITS    "rpm"
    MAX-ACCESS    read-only
    STATUS    current
    DESCRIPTION    "This shows the maximum rpm of fan module1."
    ::= { fanModule1InfoSpec 3 }

fanModule1SpecMaxAirVolume    OBJECT-TYPE
    SYNTAX    Integer32
    UNITS    "0.1 m^3/min"
    MAX-ACCESS    read-only
    STATUS    current
    DESCRIPTION    "This shows the maximum air volume of fan module1."
    ::= { fanModule1InfoSpec 4 }

fanModule1SpecMinRPM    OBJECT-TYPE
    SYNTAX    Integer32
    UNITS    "rpm"
    MAX-ACCESS    read-only
    STATUS    current
    DESCRIPTION    "This shows the minimum rpm of fan module1."
    ::= { fanModule1InfoSpec 5 }

fanModule1SpecMinAirVolume    OBJECT-TYPE
    SYNTAX    Integer32
    UNITS    "0.1 m^3/min"
    MAX-ACCESS    read-only
    STATUS    current
    DESCRIPTION    "This shows the minimum air volume of fan module1."
    ::= { fanModule1InfoSpec 6 }

fanModule1Capacity    OBJECT IDENTIFIER ::= { fanModule1 2 } 

fanModule1CapacityFan    OBJECT-TYPE
    SYNTAX    Integer32
    MAX-ACCESS    read-only
    STATUS    current
    DESCRIPTION    "This shows the capacity of fans of fan module1."
    ::= { fanModule1Capacity 1 }

fanModule1CapacityLED    OBJECT-TYPE
    SYNTAX    Integer32
    MAX-ACCESS    read-only
    STATUS    current
    DESCRIPTION    "This shows the capacity of count of LEDs of fan module1."
    ::= { fanModule1Capacity 2 }

fanModule1State    OBJECT IDENTIFIER ::= { fanModule1 4 } 

fanModule1StateSlotNum    OBJECT-TYPE
    SYNTAX    Integer32
    MAX-ACCESS    read-only
    STATUS    current
    DESCRIPTION    "This shows the number of installed slots of fan module1."
    ::= { fanModule1State 1 }

fanModule1StatePower    OBJECT-TYPE
    SYNTAX    INTEGER {
    poweroff (1), standby (2), poweron (3), unknown (4),poweron-executing (5),poweroff-executing (6)
    }
    MAX-ACCESS    read-only
    STATUS    current
    DESCRIPTION    "This shows the power supply state of fan module1."
    ::= { fanModule1State 2 }

fanModule1StateHealth    OBJECT-TYPE
    SYNTAX    INTEGER {
    normal (1),fail (2),unknown (3)
    }
    MAX-ACCESS    read-only
    STATUS    current
    DESCRIPTION    "This shows the health state of fan module1."
    ::= { fanModule1State 3 }

fanModule1StateRedundancy    OBJECT-TYPE
    SYNTAX    INTEGER {
    redundancy(1), non-redundancy(2),unknown(3)
    }
    MAX-ACCESS    read-only
    STATUS    current
    DESCRIPTION    "This shows the redundancy of fan module1."
    ::= { fanModule1State 4 }

fanModule1StateAirVolume    OBJECT-TYPE
    SYNTAX    Integer32
    UNITS    "0.1 m^3/min"
    MAX-ACCESS    read-only
    STATUS    current
    DESCRIPTION    "This shows the current air volume of fan module1."
    ::= { fanModule1State 5 }

fanModule1StateLEDTable    OBJECT-TYPE
    SYNTAX SEQUENCE OF fanModule1StateLEDEntry
    MAX-ACCESS not-accessible
    STATUS     current
    DESCRIPTION "This shows the table of LED of fan module1."
    ::= { fanModule1State 6 }

fanModule1StateLEDEntry    OBJECT-TYPE
    SYNTAX FanModule1StateLEDEntry
    MAX-ACCESS not-accessible
    STATUS    current
    DESCRIPTION "This shows the entry of LED of fan module1."
    INDEX { fanModule1StateLEDIndex }
    ::= { fanModule1StateLEDTable 1 }

fanModule1StateLEDIndex    OBJECT-TYPE
    SYNTAX    Integer32
    MAX-ACCESS    read-only
    STATUS    current
    DESCRIPTION    "This shows the index of LED of fan module1."
    ::= { fanModule1StateLEDEntry 1 }

fanModule1StateLEDName    OBJECT-TYPE
    SYNTAX    DisplayString (SIZE(0..40))
    MAX-ACCESS    read-only
    STATUS    current
    DESCRIPTION    "This shows the name of LED of fan module1."
    ::= { fanModule1StateLEDEntry 2 }

fanModule1StateLEDState    OBJECT-TYPE
    SYNTAX    INTEGER {
    turn-off(1), turn-on(2),  unknown(3), blink(4), blink-fast(5), blink-slow(6)
    }
    MAX-ACCESS    read-only
    STATUS    current
    DESCRIPTION    "This shows the state of LED of fan module1."
    ::= { fanModule1StateLEDEntry 3 }

fanModule1StateLEDColor    OBJECT-TYPE
    SYNTAX    INTEGER {
    blue (1),green (2),red (3),amber (4),unknown (5)
    }
    MAX-ACCESS    read-only
    STATUS    current
    DESCRIPTION    "This shows the color of LED of fan module1."
    ::= { fanModule1StateLEDEntry 4 }

FanModule1StateLEDEntry ::= SEQUENCE {
    fanModule1StateLEDIndex
        Integer32,
    fanModule1StateLEDName
        DisplayString,
    fanModule1StateLEDState
        INTEGER,
    fanModule1StateLEDColor
        INTEGER
}

fanModule1StateFanTable    OBJECT-TYPE
    SYNTAX SEQUENCE OF fanModule1StateFanEntry
    MAX-ACCESS not-accessible
    STATUS     current
    DESCRIPTION "This shows the table of fan of fan module1."
    ::= { fanModule1State 10 }

fanModule1StateFanEntry    OBJECT-TYPE
    SYNTAX FanModule1StateFanEntry
    MAX-ACCESS not-accessible
    STATUS    current
    DESCRIPTION "This shows the entry of fan of fan module1."
    INDEX { fanModule1StateFanIndex }
    ::= { fanModule1StateFanTable 1 }

fanModule1StateFanIndex    OBJECT-TYPE
    SYNTAX    Integer32
    MAX-ACCESS    read-only
    STATUS    current
    DESCRIPTION    "This shows the index of fan of fan module1."
    ::= { fanModule1StateFanEntry 1 }

fanModule1StateFanLocation    OBJECT-TYPE
    SYNTAX    DisplayString (SIZE(0..40))
    MAX-ACCESS    read-only
    STATUS    current
    DESCRIPTION    "This shows the location of fan of fan module1."
    ::= { fanModule1StateFanEntry 2 }

fanModule1StateFanRPM    OBJECT-TYPE
    SYNTAX    Integer32
    UNITS    "rpm"
    MAX-ACCESS    read-only
    STATUS    current
    DESCRIPTION    "This shows the rpm value of fan module1."
    ::= { fanModule1StateFanEntry 3 }

fanModule1StateFanRPMValid    OBJECT-TYPE
    SYNTAX    INTEGER {
    invalid(1), valid(2) ,unknown(3)
    }
    MAX-ACCESS    read-only
    STATUS    current
    DESCRIPTION    "This shows the validity of fan rpm value of fan module1."
    ::= { fanModule1StateFanEntry 4 }

FanModule1StateFanEntry ::= SEQUENCE {
    fanModule1StateFanIndex
        Integer32,
    fanModule1StateFanLocation
        DisplayString,
    fanModule1StateFanRPM
        Integer32,
    fanModule1StateFanRPMValid
        INTEGER
}

fanModule2    OBJECT IDENTIFIER ::= { fanModule 2 } 

fanModule2BasicInfo    OBJECT IDENTIFIER ::= { fanModule2 1 } 

fanModule2InfoType    OBJECT-TYPE
    SYNTAX    INTEGER
    MAX-ACCESS    read-only
    STATUS    current
    DESCRIPTION    "This shows the type of fan module2."
    ::= { fanModule2BasicInfo 1 }

fanModule2InfoSpec    OBJECT IDENTIFIER ::= { fanModule2BasicInfo 20 } 

fanModule2SpecPowerConsumption    OBJECT-TYPE
    SYNTAX    Integer32
    UNITS    "W"
    MAX-ACCESS    read-only
    STATUS    current
    DESCRIPTION    "This shows the power consumption of fan module2."
    ::= { fanModule2InfoSpec 1 }

fanModule2SpecMass    OBJECT-TYPE
    SYNTAX    Integer32
    UNITS    "0.1 kg"
    MAX-ACCESS    read-only
    STATUS    current
    DESCRIPTION    "This shows the weight of fan module2."
    ::= { fanModule2InfoSpec 2 }

fanModule2SpecMaxRPM    OBJECT-TYPE
    SYNTAX    Integer32
    UNITS    "rpm"
    MAX-ACCESS    read-only
    STATUS    current
    DESCRIPTION    "This shows the maximum rpm of fan module2."
    ::= { fanModule2InfoSpec 3 }

fanModule2SpecMaxAirVolume    OBJECT-TYPE
    SYNTAX    Integer32
    UNITS    "0.1 m^3/min"
    MAX-ACCESS    read-only
    STATUS    current
    DESCRIPTION    "This shows the maximum air volume of fan module2."
    ::= { fanModule2InfoSpec 4 }

fanModule2SpecMinRPM    OBJECT-TYPE
    SYNTAX    Integer32
    UNITS    "rpm"
    MAX-ACCESS    read-only
    STATUS    current
    DESCRIPTION    "This shows the minimum rpm of fan module2."
    ::= { fanModule2InfoSpec 5 }

fanModule2SpecMinAirVolume    OBJECT-TYPE
    SYNTAX    Integer32
    UNITS    "0.1 m^3/min"
    MAX-ACCESS    read-only
    STATUS    current
    DESCRIPTION    "This shows the minimum air volume of fan module2."
    ::= { fanModule2InfoSpec 6 }

fanModule2Capacity    OBJECT IDENTIFIER ::= { fanModule2 2 } 

fanModule2CapacityFan    OBJECT-TYPE
    SYNTAX    Integer32
    MAX-ACCESS    read-only
    STATUS    current
    DESCRIPTION    "This shows the capacity of fans of fan module2."
    ::= { fanModule2Capacity 1 }

fanModule2CapacityLED    OBJECT-TYPE
    SYNTAX    Integer32
    MAX-ACCESS    read-only
    STATUS    current
    DESCRIPTION    "This shows the capacity of count of LEDs of fan module2."
    ::= { fanModule2Capacity 2 }

fanModule2State    OBJECT IDENTIFIER ::= { fanModule2 4 } 

fanModule2StateSlotNum    OBJECT-TYPE
    SYNTAX    Integer32
    MAX-ACCESS    read-only
    STATUS    current
    DESCRIPTION    "This shows the number of installed slots of fan module2."
    ::= { fanModule2State 1 }

fanModule2StatePower    OBJECT-TYPE
    SYNTAX    INTEGER {
    poweroff (1), standby (2), poweron (3), unknown (4),poweron-executing (5),poweroff-executing (6)
    }
    MAX-ACCESS    read-only
    STATUS    current
    DESCRIPTION    "This shows the power supply state of fan module2."
    ::= { fanModule2State 2 }

fanModule2StateHealth    OBJECT-TYPE
    SYNTAX    INTEGER {
    normal (1),fail (2),unknown (3)
    }
    MAX-ACCESS    read-only
    STATUS    current
    DESCRIPTION    "This shows the health state of fan module2."
    ::= { fanModule2State 3 }

fanModule2StateRedundancy    OBJECT-TYPE
    SYNTAX    INTEGER {
    redundancy(1), non-redundancy(2),unknown(3)
    }
    MAX-ACCESS    read-only
    STATUS    current
    DESCRIPTION    "This shows the redundancy of fan module2."
    ::= { fanModule2State 4 }

fanModule2StateAirVolume    OBJECT-TYPE
    SYNTAX    Integer32
    UNITS    "0.1 m^3/min"
    MAX-ACCESS    read-only
    STATUS    current
    DESCRIPTION    "This shows the current air volume of fan module2."
    ::= { fanModule2State 5 }

fanModule2StateLEDTable    OBJECT-TYPE
    SYNTAX SEQUENCE OF fanModule2StateLEDEntry
    MAX-ACCESS not-accessible
    STATUS     current
    DESCRIPTION "This shows the table of LED of fan module2."
    ::= { fanModule2State 6 }

fanModule2StateLEDEntry    OBJECT-TYPE
    SYNTAX FanModule2StateLEDEntry
    MAX-ACCESS not-accessible
    STATUS    current
    DESCRIPTION "This shows the entry of LED of fan module2."
    INDEX { fanModule2StateLEDIndex }
    ::= { fanModule2StateLEDTable 1 }

fanModule2StateLEDIndex    OBJECT-TYPE
    SYNTAX    Integer32
    MAX-ACCESS    read-only
    STATUS    current
    DESCRIPTION    "This shows the index of LED of fan module2."
    ::= { fanModule2StateLEDEntry 1 }

fanModule2StateLEDName    OBJECT-TYPE
    SYNTAX    DisplayString (SIZE(0..40))
    MAX-ACCESS    read-only
    STATUS    current
    DESCRIPTION    "This shows the name of LED of fan module2."
    ::= { fanModule2StateLEDEntry 2 }

fanModule2StateLEDState    OBJECT-TYPE
    SYNTAX    INTEGER {
    turn-off(1), turn-on(2),  unknown(3), blink(4), blink-fast(5), blink-slow(6)
    }
    MAX-ACCESS    read-only
    STATUS    current
    DESCRIPTION    "This shows the state of LED of fan module2."
    ::= { fanModule2StateLEDEntry 3 }

fanModule2StateLEDColor    OBJECT-TYPE
    SYNTAX    INTEGER {
    blue (1),green (2),red (3),amber (4),unknown (5)
    }
    MAX-ACCESS    read-only
    STATUS    current
    DESCRIPTION    "This shows the color of LED of fan module2."
    ::= { fanModule2StateLEDEntry 4 }

FanModule2StateLEDEntry ::= SEQUENCE {
    fanModule2StateLEDIndex
        Integer32,
    fanModule2StateLEDName
        DisplayString,
    fanModule2StateLEDState
        INTEGER,
    fanModule2StateLEDColor
        INTEGER
}

fanModule2StateFanTable    OBJECT-TYPE
    SYNTAX SEQUENCE OF fanModule2StateFanEntry
    MAX-ACCESS not-accessible
    STATUS     current
    DESCRIPTION "This shows the table of fan of fan module2."
    ::= { fanModule2State 10 }

fanModule2StateFanEntry    OBJECT-TYPE
    SYNTAX FanModule2StateFanEntry
    MAX-ACCESS not-accessible
    STATUS    current
    DESCRIPTION "This shows the entry of fan of fan module2."
    INDEX { fanModule2StateFanIndex }
    ::= { fanModule2StateFanTable 1 }

fanModule2StateFanIndex    OBJECT-TYPE
    SYNTAX    Integer32
    MAX-ACCESS    read-only
    STATUS    current
    DESCRIPTION    "This shows the index of fan of fan module2."
    ::= { fanModule2StateFanEntry 1 }

fanModule2StateFanLocation    OBJECT-TYPE
    SYNTAX    DisplayString (SIZE(0..40))
    MAX-ACCESS    read-only
    STATUS    current
    DESCRIPTION    "This shows the location of fan of fan module2."
    ::= { fanModule2StateFanEntry 2 }

fanModule2StateFanRPM    OBJECT-TYPE
    SYNTAX    Integer32
    UNITS    "rpm"
    MAX-ACCESS    read-only
    STATUS    current
    DESCRIPTION    "This shows the rpm value of fan module2."
    ::= { fanModule2StateFanEntry 3 }

fanModule2StateFanRPMValid    OBJECT-TYPE
    SYNTAX    INTEGER {
    invalid(1), valid(2) ,unknown(3)
    }
    MAX-ACCESS    read-only
    STATUS    current
    DESCRIPTION    "This shows the validity of fan rpm value of fan module2."
    ::= { fanModule2StateFanEntry 4 }

FanModule2StateFanEntry ::= SEQUENCE {
    fanModule2StateFanIndex
        Integer32,
    fanModule2StateFanLocation
        DisplayString,
    fanModule2StateFanRPM
        Integer32,
    fanModule2StateFanRPMValid
        INTEGER
}

fanModule3    OBJECT IDENTIFIER ::= { fanModule 3 } 

fanModule3BasicInfo    OBJECT IDENTIFIER ::= { fanModule3 1 } 

fanModule3InfoType    OBJECT-TYPE
    SYNTAX    INTEGER
    MAX-ACCESS    read-only
    STATUS    current
    DESCRIPTION    "This shows the type of fan module3."
    ::= { fanModule3BasicInfo 1 }

fanModule3InfoSpec    OBJECT IDENTIFIER ::= { fanModule3BasicInfo 20 } 

fanModule3SpecPowerConsumption    OBJECT-TYPE
    SYNTAX    Integer32
    UNITS    "W"
    MAX-ACCESS    read-only
    STATUS    current
    DESCRIPTION    "This shows the power consumption of fan module3."
    ::= { fanModule3InfoSpec 1 }

fanModule3SpecMass    OBJECT-TYPE
    SYNTAX    Integer32
    UNITS    "0.1 kg"
    MAX-ACCESS    read-only
    STATUS    current
    DESCRIPTION    "This shows the weight of fan module3."
    ::= { fanModule3InfoSpec 2 }

fanModule3SpecMaxRPM    OBJECT-TYPE
    SYNTAX    Integer32
    UNITS    "rpm"
    MAX-ACCESS    read-only
    STATUS    current
    DESCRIPTION    "This shows the maximum rpm of fan module3."
    ::= { fanModule3InfoSpec 3 }

fanModule3SpecMaxAirVolume    OBJECT-TYPE
    SYNTAX    Integer32
    UNITS    "0.1 m^3/min"
    MAX-ACCESS    read-only
    STATUS    current
    DESCRIPTION    "This shows the maximum air volume of fan module3."
    ::= { fanModule3InfoSpec 4 }

fanModule3SpecMinRPM    OBJECT-TYPE
    SYNTAX    Integer32
    UNITS    "rpm"
    MAX-ACCESS    read-only
    STATUS    current
    DESCRIPTION    "This shows the minimum rpm of fan module3."
    ::= { fanModule3InfoSpec 5 }

fanModule3SpecMinAirVolume    OBJECT-TYPE
    SYNTAX    Integer32
    UNITS    "0.1 m^3/min"
    MAX-ACCESS    read-only
    STATUS    current
    DESCRIPTION    "This shows the minimum air volume of fan module3."
    ::= { fanModule3InfoSpec 6 }

fanModule3Capacity    OBJECT IDENTIFIER ::= { fanModule3 2 } 

fanModule3CapacityFan    OBJECT-TYPE
    SYNTAX    Integer32
    MAX-ACCESS    read-only
    STATUS    current
    DESCRIPTION    "This shows the capacity of fans of fan module3."
    ::= { fanModule3Capacity 1 }

fanModule3CapacityLED    OBJECT-TYPE
    SYNTAX    Integer32
    MAX-ACCESS    read-only
    STATUS    current
    DESCRIPTION    "This shows the capacity of count of LEDs of fan module3."
    ::= { fanModule3Capacity 2 }

fanModule3State    OBJECT IDENTIFIER ::= { fanModule3 4 } 

fanModule3StateSlotNum    OBJECT-TYPE
    SYNTAX    Integer32
    MAX-ACCESS    read-only
    STATUS    current
    DESCRIPTION    "This shows the number of installed slots of fan module3."
    ::= { fanModule3State 1 }

fanModule3StatePower    OBJECT-TYPE
    SYNTAX    INTEGER {
    poweroff (1), standby (2), poweron (3), unknown (4),poweron-executing (5),poweroff-executing (6)
    }
    MAX-ACCESS    read-only
    STATUS    current
    DESCRIPTION    "This shows the power supply state of fan module3."
    ::= { fanModule3State 2 }

fanModule3StateHealth    OBJECT-TYPE
    SYNTAX    INTEGER {
    normal (1),fail (2),unknown (3)
    }
    MAX-ACCESS    read-only
    STATUS    current
    DESCRIPTION    "This shows the health state of fan module3."
    ::= { fanModule3State 3 }

fanModule3StateRedundancy    OBJECT-TYPE
    SYNTAX    INTEGER {
    redundancy(1), non-redundancy(2),unknown(3)
    }
    MAX-ACCESS    read-only
    STATUS    current
    DESCRIPTION    "This shows the redundancy of fan module3."
    ::= { fanModule3State 4 }

fanModule3StateAirVolume    OBJECT-TYPE
    SYNTAX    Integer32
    UNITS    "0.1 m^3/min"
    MAX-ACCESS    read-only
    STATUS    current
    DESCRIPTION    "This shows the current air volume of fan module3."
    ::= { fanModule3State 5 }

fanModule3StateLEDTable    OBJECT-TYPE
    SYNTAX SEQUENCE OF fanModule3StateLEDEntry
    MAX-ACCESS not-accessible
    STATUS     current
    DESCRIPTION "This shows the table of LED of fan module3."
    ::= { fanModule3State 6 }

fanModule3StateLEDEntry    OBJECT-TYPE
    SYNTAX FanModule3StateLEDEntry
    MAX-ACCESS not-accessible
    STATUS    current
    DESCRIPTION "This shows the entry of LED of fan module3."
    INDEX { fanModule3StateLEDIndex }
    ::= { fanModule3StateLEDTable 1 }

fanModule3StateLEDIndex    OBJECT-TYPE
    SYNTAX    Integer32
    MAX-ACCESS    read-only
    STATUS    current
    DESCRIPTION    "This shows the index of LED of fan module3."
    ::= { fanModule3StateLEDEntry 1 }

fanModule3StateLEDName    OBJECT-TYPE
    SYNTAX    DisplayString (SIZE(0..40))
    MAX-ACCESS    read-only
    STATUS    current
    DESCRIPTION    "This shows the name of LED of fan module3."
    ::= { fanModule3StateLEDEntry 2 }

fanModule3StateLEDState    OBJECT-TYPE
    SYNTAX    INTEGER {
    turn-off(1), turn-on(2),  unknown(3), blink(4), blink-fast(5), blink-slow(6)
    }
    MAX-ACCESS    read-only
    STATUS    current
    DESCRIPTION    "This shows the state of LED of fan module3."
    ::= { fanModule3StateLEDEntry 3 }

fanModule3StateLEDColor    OBJECT-TYPE
    SYNTAX    INTEGER {
    blue (1),green (2),red (3),amber (4),unknown (5)
    }
    MAX-ACCESS    read-only
    STATUS    current
    DESCRIPTION    "This shows the color of LED of fan module3."
    ::= { fanModule3StateLEDEntry 4 }

FanModule3StateLEDEntry ::= SEQUENCE {
    fanModule3StateLEDIndex
        Integer32,
    fanModule3StateLEDName
        DisplayString,
    fanModule3StateLEDState
        INTEGER,
    fanModule3StateLEDColor
        INTEGER
}

fanModule3StateFanTable    OBJECT-TYPE
    SYNTAX SEQUENCE OF fanModule3StateFanEntry
    MAX-ACCESS not-accessible
    STATUS     current
    DESCRIPTION "This shows the table of fan of fan module3."
    ::= { fanModule3State 10 }

fanModule3StateFanEntry    OBJECT-TYPE
    SYNTAX FanModule3StateFanEntry
    MAX-ACCESS not-accessible
    STATUS    current
    DESCRIPTION "This shows the entry of fan of fan module3."
    INDEX { fanModule3StateFanIndex }
    ::= { fanModule3StateFanTable 1 }

fanModule3StateFanIndex    OBJECT-TYPE
    SYNTAX    Integer32
    MAX-ACCESS    read-only
    STATUS    current
    DESCRIPTION    "This shows the index of fan of fan module3."
    ::= { fanModule3StateFanEntry 1 }

fanModule3StateFanLocation    OBJECT-TYPE
    SYNTAX    DisplayString (SIZE(0..40))
    MAX-ACCESS    read-only
    STATUS    current
    DESCRIPTION    "This shows the location of fan of fan module3."
    ::= { fanModule3StateFanEntry 2 }

fanModule3StateFanRPM    OBJECT-TYPE
    SYNTAX    Integer32
    UNITS    "rpm"
    MAX-ACCESS    read-only
    STATUS    current
    DESCRIPTION    "This shows the rpm value of fan module3."
    ::= { fanModule3StateFanEntry 3 }

fanModule3StateFanRPMValid    OBJECT-TYPE
    SYNTAX    INTEGER {
    invalid(1), valid(2) ,unknown(3)
    }
    MAX-ACCESS    read-only
    STATUS    current
    DESCRIPTION    "This shows the validity of fan rpm value of fan module3."
    ::= { fanModule3StateFanEntry 4 }

FanModule3StateFanEntry ::= SEQUENCE {
    fanModule3StateFanIndex
        Integer32,
    fanModule3StateFanLocation
        DisplayString,
    fanModule3StateFanRPM
        Integer32,
    fanModule3StateFanRPMValid
        INTEGER
}

fanModule4    OBJECT IDENTIFIER ::= { fanModule 4 } 

fanModule4BasicInfo    OBJECT IDENTIFIER ::= { fanModule4 1 } 

fanModule4InfoType    OBJECT-TYPE
    SYNTAX    INTEGER
    MAX-ACCESS    read-only
    STATUS    current
    DESCRIPTION    "This shows the type of fan module4."
    ::= { fanModule4BasicInfo 1 }

fanModule4InfoSpec    OBJECT IDENTIFIER ::= { fanModule4BasicInfo 20 } 

fanModule4SpecPowerConsumption    OBJECT-TYPE
    SYNTAX    Integer32
    UNITS    "W"
    MAX-ACCESS    read-only
    STATUS    current
    DESCRIPTION    "This shows the power consumption of fan module4."
    ::= { fanModule4InfoSpec 1 }

fanModule4SpecMass    OBJECT-TYPE
    SYNTAX    Integer32
    UNITS    "0.1 kg"
    MAX-ACCESS    read-only
    STATUS    current
    DESCRIPTION    "This shows the weight of fan module4."
    ::= { fanModule4InfoSpec 2 }

fanModule4SpecMaxRPM    OBJECT-TYPE
    SYNTAX    Integer32
    UNITS    "rpm"
    MAX-ACCESS    read-only
    STATUS    current
    DESCRIPTION    "This shows the maximum rpm of fan module4."
    ::= { fanModule4InfoSpec 3 }

fanModule4SpecMaxAirVolume    OBJECT-TYPE
    SYNTAX    Integer32
    UNITS    "0.1 m^3/min"
    MAX-ACCESS    read-only
    STATUS    current
    DESCRIPTION    "This shows the maximum air volume of fan module4."
    ::= { fanModule4InfoSpec 4 }

fanModule4SpecMinRPM    OBJECT-TYPE
    SYNTAX    Integer32
    UNITS    "rpm"
    MAX-ACCESS    read-only
    STATUS    current
    DESCRIPTION    "This shows the minimum rpm of fan module4."
    ::= { fanModule4InfoSpec 5 }

fanModule4SpecMinAirVolume    OBJECT-TYPE
    SYNTAX    Integer32
    UNITS    "0.1 m^3/min"
    MAX-ACCESS    read-only
    STATUS    current
    DESCRIPTION    "This shows the minimum air volume of fan module4."
    ::= { fanModule4InfoSpec 6 }

fanModule4Capacity    OBJECT IDENTIFIER ::= { fanModule4 2 } 

fanModule4CapacityFan    OBJECT-TYPE
    SYNTAX    Integer32
    MAX-ACCESS    read-only
    STATUS    current
    DESCRIPTION    "This shows the capacity of fans of fan module4."
    ::= { fanModule4Capacity 1 }

fanModule4CapacityLED    OBJECT-TYPE
    SYNTAX    Integer32
    MAX-ACCESS    read-only
    STATUS    current
    DESCRIPTION    "This shows the capacity of count of LEDs of fan module4."
    ::= { fanModule4Capacity 2 }

fanModule4State    OBJECT IDENTIFIER ::= { fanModule4 4 } 

fanModule4StateSlotNum    OBJECT-TYPE
    SYNTAX    Integer32
    MAX-ACCESS    read-only
    STATUS    current
    DESCRIPTION    "This shows the number of installed slots of fan module4."
    ::= { fanModule4State 1 }

fanModule4StatePower    OBJECT-TYPE
    SYNTAX    INTEGER {
    poweroff (1), standby (2), poweron (3), unknown (4),poweron-executing (5),poweroff-executing (6)
    }
    MAX-ACCESS    read-only
    STATUS    current
    DESCRIPTION    "This shows the power supply state of fan module4."
    ::= { fanModule4State 2 }

fanModule4StateHealth    OBJECT-TYPE
    SYNTAX    INTEGER {
    normal (1),fail (2),unknown (3)
    }
    MAX-ACCESS    read-only
    STATUS    current
    DESCRIPTION    "This shows the health state of fan module4."
    ::= { fanModule4State 3 }

fanModule4StateRedundancy    OBJECT-TYPE
    SYNTAX    INTEGER {
    redundancy(1), non-redundancy(2),unknown(3)
    }
    MAX-ACCESS    read-only
    STATUS    current
    DESCRIPTION    "This shows the redundancy of fan module4."
    ::= { fanModule4State 4 }

fanModule4StateAirVolume    OBJECT-TYPE
    SYNTAX    Integer32
    UNITS    "0.1 m^3/min"
    MAX-ACCESS    read-only
    STATUS    current
    DESCRIPTION    "This shows the current air volume of fan module4."
    ::= { fanModule4State 5 }

fanModule4StateLEDTable    OBJECT-TYPE
    SYNTAX SEQUENCE OF fanModule4StateLEDEntry
    MAX-ACCESS not-accessible
    STATUS     current
    DESCRIPTION "This shows the table of LED of fan module4."
    ::= { fanModule4State 6 }

fanModule4StateLEDEntry    OBJECT-TYPE
    SYNTAX FanModule4StateLEDEntry
    MAX-ACCESS not-accessible
    STATUS    current
    DESCRIPTION "This shows the entry of LED of fan module4."
    INDEX { fanModule4StateLEDIndex }
    ::= { fanModule4StateLEDTable 1 }

fanModule4StateLEDIndex    OBJECT-TYPE
    SYNTAX    Integer32
    MAX-ACCESS    read-only
    STATUS    current
    DESCRIPTION    "This shows the index of LED of fan module4."
    ::= { fanModule4StateLEDEntry 1 }

fanModule4StateLEDName    OBJECT-TYPE
    SYNTAX    DisplayString (SIZE(0..40))
    MAX-ACCESS    read-only
    STATUS    current
    DESCRIPTION    "This shows the name of LED of fan module4."
    ::= { fanModule4StateLEDEntry 2 }

fanModule4StateLEDState    OBJECT-TYPE
    SYNTAX    INTEGER {
    turn-off(1), turn-on(2),  unknown(3), blink(4), blink-fast(5), blink-slow(6)
    }
    MAX-ACCESS    read-only
    STATUS    current
    DESCRIPTION    "This shows the state of LED of fan module4."
    ::= { fanModule4StateLEDEntry 3 }

fanModule4StateLEDColor    OBJECT-TYPE
    SYNTAX    INTEGER {
    blue (1),green (2),red (3),amber (4),unknown (5)
    }
    MAX-ACCESS    read-only
    STATUS    current
    DESCRIPTION    "This shows the color of LED of fan module4."
    ::= { fanModule4StateLEDEntry 4 }

FanModule4StateLEDEntry ::= SEQUENCE {
    fanModule4StateLEDIndex
        Integer32,
    fanModule4StateLEDName
        DisplayString,
    fanModule4StateLEDState
        INTEGER,
    fanModule4StateLEDColor
        INTEGER
}

fanModule4StateFanTable    OBJECT-TYPE
    SYNTAX SEQUENCE OF fanModule4StateFanEntry
    MAX-ACCESS not-accessible
    STATUS     current
    DESCRIPTION "This shows the table of fan of fan module4."
    ::= { fanModule4State 10 }

fanModule4StateFanEntry    OBJECT-TYPE
    SYNTAX FanModule4StateFanEntry
    MAX-ACCESS not-accessible
    STATUS    current
    DESCRIPTION "This shows the entry of fan of fan module4."
    INDEX { fanModule4StateFanIndex }
    ::= { fanModule4StateFanTable 1 }

fanModule4StateFanIndex    OBJECT-TYPE
    SYNTAX    Integer32
    MAX-ACCESS    read-only
    STATUS    current
    DESCRIPTION    "This shows the index of fan of fan module4."
    ::= { fanModule4StateFanEntry 1 }

fanModule4StateFanLocation    OBJECT-TYPE
    SYNTAX    DisplayString (SIZE(0..40))
    MAX-ACCESS    read-only
    STATUS    current
    DESCRIPTION    "This shows the location of fan of fan module4."
    ::= { fanModule4StateFanEntry 2 }

fanModule4StateFanRPM    OBJECT-TYPE
    SYNTAX    Integer32
    UNITS    "rpm"
    MAX-ACCESS    read-only
    STATUS    current
    DESCRIPTION    "This shows the rpm value of fan module4."
    ::= { fanModule4StateFanEntry 3 }

fanModule4StateFanRPMValid    OBJECT-TYPE
    SYNTAX    INTEGER {
    invalid(1), valid(2) ,unknown(3)
    }
    MAX-ACCESS    read-only
    STATUS    current
    DESCRIPTION    "This shows the validity of fan rpm value of fan module4."
    ::= { fanModule4StateFanEntry 4 }

FanModule4StateFanEntry ::= SEQUENCE {
    fanModule4StateFanIndex
        Integer32,
    fanModule4StateFanLocation
        DisplayString,
    fanModule4StateFanRPM
        Integer32,
    fanModule4StateFanRPMValid
        INTEGER
}

fanModule5    OBJECT IDENTIFIER ::= { fanModule 5 } 

fanModule5BasicInfo    OBJECT IDENTIFIER ::= { fanModule5 1 } 

fanModule5InfoType    OBJECT-TYPE
    SYNTAX    INTEGER
    MAX-ACCESS    read-only
    STATUS    current
    DESCRIPTION    "This shows the type of fan module5."
    ::= { fanModule5BasicInfo 1 }

fanModule5InfoSpec    OBJECT IDENTIFIER ::= { fanModule5BasicInfo 20 } 

fanModule5SpecPowerConsumption    OBJECT-TYPE
    SYNTAX    Integer32
    UNITS    "W"
    MAX-ACCESS    read-only
    STATUS    current
    DESCRIPTION    "This shows the power consumption of fan module5."
    ::= { fanModule5InfoSpec 1 }

fanModule5SpecMass    OBJECT-TYPE
    SYNTAX    Integer32
    UNITS    "0.1 kg"
    MAX-ACCESS    read-only
    STATUS    current
    DESCRIPTION    "This shows the weight of fan module5."
    ::= { fanModule5InfoSpec 2 }

fanModule5SpecMaxRPM    OBJECT-TYPE
    SYNTAX    Integer32
    UNITS    "rpm"
    MAX-ACCESS    read-only
    STATUS    current
    DESCRIPTION    "This shows the maximum rpm of fan module5."
    ::= { fanModule5InfoSpec 3 }

fanModule5SpecMaxAirVolume    OBJECT-TYPE
    SYNTAX    Integer32
    UNITS    "0.1 m^3/min"
    MAX-ACCESS    read-only
    STATUS    current
    DESCRIPTION    "This shows the maximum air volume of fan module5."
    ::= { fanModule5InfoSpec 4 }

fanModule5SpecMinRPM    OBJECT-TYPE
    SYNTAX    Integer32
    UNITS    "rpm"
    MAX-ACCESS    read-only
    STATUS    current
    DESCRIPTION    "This shows the minimum rpm of fan module5."
    ::= { fanModule5InfoSpec 5 }

fanModule5SpecMinAirVolume    OBJECT-TYPE
    SYNTAX    Integer32
    UNITS    "0.1 m^3/min"
    MAX-ACCESS    read-only
    STATUS    current
    DESCRIPTION    "This shows the minimum air volume of fan module5."
    ::= { fanModule5InfoSpec 6 }

fanModule5Capacity    OBJECT IDENTIFIER ::= { fanModule5 2 } 

fanModule5CapacityFan    OBJECT-TYPE
    SYNTAX    Integer32
    MAX-ACCESS    read-only
    STATUS    current
    DESCRIPTION    "This shows the capacity of fans of fan module5."
    ::= { fanModule5Capacity 1 }

fanModule5CapacityLED    OBJECT-TYPE
    SYNTAX    Integer32
    MAX-ACCESS    read-only
    STATUS    current
    DESCRIPTION    "This shows the capacity of count of LEDs of fan module5."
    ::= { fanModule5Capacity 2 }

fanModule5State    OBJECT IDENTIFIER ::= { fanModule5 4 } 

fanModule5StateSlotNum    OBJECT-TYPE
    SYNTAX    Integer32
    MAX-ACCESS    read-only
    STATUS    current
    DESCRIPTION    "This shows the number of installed slots of fan module5."
    ::= { fanModule5State 1 }

fanModule5StatePower    OBJECT-TYPE
    SYNTAX    INTEGER {
    poweroff (1), standby (2), poweron (3), unknown (4),poweron-executing (5),poweroff-executing (6)
    }
    MAX-ACCESS    read-only
    STATUS    current
    DESCRIPTION    "This shows the power supply state of fan module5."
    ::= { fanModule5State 2 }

fanModule5StateHealth    OBJECT-TYPE
    SYNTAX    INTEGER {
    normal (1),fail (2),unknown (3)
    }
    MAX-ACCESS    read-only
    STATUS    current
    DESCRIPTION    "This shows the health state of fan module5."
    ::= { fanModule5State 3 }

fanModule5StateRedundancy    OBJECT-TYPE
    SYNTAX    INTEGER {
    redundancy(1), non-redundancy(2),unknown(3)
    }
    MAX-ACCESS    read-only
    STATUS    current
    DESCRIPTION    "This shows the redundancy of fan module5."
    ::= { fanModule5State 4 }

fanModule5StateAirVolume    OBJECT-TYPE
    SYNTAX    Integer32
    UNITS    "0.1 m^3/min"
    MAX-ACCESS    read-only
    STATUS    current
    DESCRIPTION    "This shows the current air volume of fan module5."
    ::= { fanModule5State 5 }

fanModule5StateLEDTable    OBJECT-TYPE
    SYNTAX SEQUENCE OF fanModule5StateLEDEntry
    MAX-ACCESS not-accessible
    STATUS     current
    DESCRIPTION "This shows the table of LED of fan module5."
    ::= { fanModule5State 6 }

fanModule5StateLEDEntry    OBJECT-TYPE
    SYNTAX FanModule5StateLEDEntry
    MAX-ACCESS not-accessible
    STATUS    current
    DESCRIPTION "This shows the entry of LED of fan module5."
    INDEX { fanModule5StateLEDIndex }
    ::= { fanModule5StateLEDTable 1 }

fanModule5StateLEDIndex    OBJECT-TYPE
    SYNTAX    Integer32
    MAX-ACCESS    read-only
    STATUS    current
    DESCRIPTION    "This shows the index of LED of fan module5."
    ::= { fanModule5StateLEDEntry 1 }

fanModule5StateLEDName    OBJECT-TYPE
    SYNTAX    DisplayString (SIZE(0..40))
    MAX-ACCESS    read-only
    STATUS    current
    DESCRIPTION    "This shows the name of LED of fan module5."
    ::= { fanModule5StateLEDEntry 2 }

fanModule5StateLEDState    OBJECT-TYPE
    SYNTAX    INTEGER {
    turn-off(1), turn-on(2),  unknown(3), blink(4), blink-fast(5), blink-slow(6)
    }
    MAX-ACCESS    read-only
    STATUS    current
    DESCRIPTION    "This shows the state of LED of fan module5."
    ::= { fanModule5StateLEDEntry 3 }

fanModule5StateLEDColor    OBJECT-TYPE
    SYNTAX    INTEGER {
    blue (1),green (2),red (3),amber (4),unknown (5)
    }
    MAX-ACCESS    read-only
    STATUS    current
    DESCRIPTION    "This shows the color of LED of fan module5."
    ::= { fanModule5StateLEDEntry 4 }

FanModule5StateLEDEntry ::= SEQUENCE {
    fanModule5StateLEDIndex
        Integer32,
    fanModule5StateLEDName
        DisplayString,
    fanModule5StateLEDState
        INTEGER,
    fanModule5StateLEDColor
        INTEGER
}

fanModule5StateFanTable    OBJECT-TYPE
    SYNTAX SEQUENCE OF fanModule5StateFanEntry
    MAX-ACCESS not-accessible
    STATUS     current
    DESCRIPTION "This shows the table of fan of fan module5."
    ::= { fanModule5State 10 }

fanModule5StateFanEntry    OBJECT-TYPE
    SYNTAX FanModule5StateFanEntry
    MAX-ACCESS not-accessible
    STATUS    current
    DESCRIPTION "This shows the entry of fan of fan module5."
    INDEX { fanModule5StateFanIndex }
    ::= { fanModule5StateFanTable 1 }

fanModule5StateFanIndex    OBJECT-TYPE
    SYNTAX    Integer32
    MAX-ACCESS    read-only
    STATUS    current
    DESCRIPTION    "This shows the index of fan of fan module5."
    ::= { fanModule5StateFanEntry 1 }

fanModule5StateFanLocation    OBJECT-TYPE
    SYNTAX    DisplayString (SIZE(0..40))
    MAX-ACCESS    read-only
    STATUS    current
    DESCRIPTION    "This shows the location of fan of fan module5."
    ::= { fanModule5StateFanEntry 2 }

fanModule5StateFanRPM    OBJECT-TYPE
    SYNTAX    Integer32
    UNITS    "rpm"
    MAX-ACCESS    read-only
    STATUS    current
    DESCRIPTION    "This shows the rpm value of fan module5."
    ::= { fanModule5StateFanEntry 3 }

fanModule5StateFanRPMValid    OBJECT-TYPE
    SYNTAX    INTEGER {
    invalid(1), valid(2) ,unknown(3)
    }
    MAX-ACCESS    read-only
    STATUS    current
    DESCRIPTION    "This shows the validity of fan rpm value of fan module5."
    ::= { fanModule5StateFanEntry 4 }

FanModule5StateFanEntry ::= SEQUENCE {
    fanModule5StateFanIndex
        Integer32,
    fanModule5StateFanLocation
        DisplayString,
    fanModule5StateFanRPM
        Integer32,
    fanModule5StateFanRPMValid
        INTEGER
}

fanModule6    OBJECT IDENTIFIER ::= { fanModule 6 } 

fanModule6BasicInfo    OBJECT IDENTIFIER ::= { fanModule6 1 } 

fanModule6InfoType    OBJECT-TYPE
    SYNTAX    INTEGER
    MAX-ACCESS    read-only
    STATUS    current
    DESCRIPTION    "This shows the type of fan module6."
    ::= { fanModule6BasicInfo 1 }

fanModule6InfoSpec    OBJECT IDENTIFIER ::= { fanModule6BasicInfo 20 } 

fanModule6SpecPowerConsumption    OBJECT-TYPE
    SYNTAX    Integer32
    UNITS    "W"
    MAX-ACCESS    read-only
    STATUS    current
    DESCRIPTION    "This shows the power consumption of fan module6."
    ::= { fanModule6InfoSpec 1 }

fanModule6SpecMass    OBJECT-TYPE
    SYNTAX    Integer32
    UNITS    "0.1 kg"
    MAX-ACCESS    read-only
    STATUS    current
    DESCRIPTION    "This shows the weight of fan module6."
    ::= { fanModule6InfoSpec 2 }

fanModule6SpecMaxRPM    OBJECT-TYPE
    SYNTAX    Integer32
    UNITS    "rpm"
    MAX-ACCESS    read-only
    STATUS    current
    DESCRIPTION    "This shows the maximum rpm of fan module6."
    ::= { fanModule6InfoSpec 3 }

fanModule6SpecMaxAirVolume    OBJECT-TYPE
    SYNTAX    Integer32
    UNITS    "0.1 m^3/min"
    MAX-ACCESS    read-only
    STATUS    current
    DESCRIPTION    "This shows the maximum air volume of fan module6."
    ::= { fanModule6InfoSpec 4 }

fanModule6SpecMinRPM    OBJECT-TYPE
    SYNTAX    Integer32
    UNITS    "rpm"
    MAX-ACCESS    read-only
    STATUS    current
    DESCRIPTION    "This shows the minimum rpm of fan module6."
    ::= { fanModule6InfoSpec 5 }

fanModule6SpecMinAirVolume    OBJECT-TYPE
    SYNTAX    Integer32
    UNITS    "0.1 m^3/min"
    MAX-ACCESS    read-only
    STATUS    current
    DESCRIPTION    "This shows the minimum air volume of fan module6."
    ::= { fanModule6InfoSpec 6 }

fanModule6Capacity    OBJECT IDENTIFIER ::= { fanModule6 2 } 

fanModule6CapacityFan    OBJECT-TYPE
    SYNTAX    Integer32
    MAX-ACCESS    read-only
    STATUS    current
    DESCRIPTION    "This shows the capacity of fans of fan module6."
    ::= { fanModule6Capacity 1 }

fanModule6CapacityLED    OBJECT-TYPE
    SYNTAX    Integer32
    MAX-ACCESS    read-only
    STATUS    current
    DESCRIPTION    "This shows the capacity of count of LEDs of fan module6."
    ::= { fanModule6Capacity 2 }

fanModule6State    OBJECT IDENTIFIER ::= { fanModule6 4 } 

fanModule6StateSlotNum    OBJECT-TYPE
    SYNTAX    Integer32
    MAX-ACCESS    read-only
    STATUS    current
    DESCRIPTION    "This shows the number of installed slots of fan module6."
    ::= { fanModule6State 1 }

fanModule6StatePower    OBJECT-TYPE
    SYNTAX    INTEGER {
    poweroff (1), standby (2), poweron (3), unknown (4),poweron-executing (5),poweroff-executing (6)
    }
    MAX-ACCESS    read-only
    STATUS    current
    DESCRIPTION    "This shows the power supply state of fan module6."
    ::= { fanModule6State 2 }

fanModule6StateHealth    OBJECT-TYPE
    SYNTAX    INTEGER {
    normal (1),fail (2),unknown (3)
    }
    MAX-ACCESS    read-only
    STATUS    current
    DESCRIPTION    "This shows the health state of fan module6."
    ::= { fanModule6State 3 }

fanModule6StateRedundancy    OBJECT-TYPE
    SYNTAX    INTEGER {
    redundancy(1), non-redundancy(2),unknown(3)
    }
    MAX-ACCESS    read-only
    STATUS    current
    DESCRIPTION    "This shows the redundancy of fan module6."
    ::= { fanModule6State 4 }

fanModule6StateAirVolume    OBJECT-TYPE
    SYNTAX    Integer32
    UNITS    "0.1 m^3/min"
    MAX-ACCESS    read-only
    STATUS    current
    DESCRIPTION    "This shows the current air volume of fan module6."
    ::= { fanModule6State 5 }

fanModule6StateLEDTable    OBJECT-TYPE
    SYNTAX SEQUENCE OF fanModule6StateLEDEntry
    MAX-ACCESS not-accessible
    STATUS     current
    DESCRIPTION "This shows the table of LED of fan module6."
    ::= { fanModule6State 6 }

fanModule6StateLEDEntry    OBJECT-TYPE
    SYNTAX FanModule6StateLEDEntry
    MAX-ACCESS not-accessible
    STATUS    current
    DESCRIPTION "This shows the entry of LED of fan module6."
    INDEX { fanModule6StateLEDIndex }
    ::= { fanModule6StateLEDTable 1 }

fanModule6StateLEDIndex    OBJECT-TYPE
    SYNTAX    Integer32
    MAX-ACCESS    read-only
    STATUS    current
    DESCRIPTION    "This shows the index of LED of fan module6."
    ::= { fanModule6StateLEDEntry 1 }

fanModule6StateLEDName    OBJECT-TYPE
    SYNTAX    DisplayString (SIZE(0..40))
    MAX-ACCESS    read-only
    STATUS    current
    DESCRIPTION    "This shows the name of LED of fan module6."
    ::= { fanModule6StateLEDEntry 2 }

fanModule6StateLEDState    OBJECT-TYPE
    SYNTAX    INTEGER {
    turn-off(1), turn-on(2),  unknown(3), blink(4), blink-fast(5), blink-slow(6)
    }
    MAX-ACCESS    read-only
    STATUS    current
    DESCRIPTION    "This shows the state of LED of fan module6."
    ::= { fanModule6StateLEDEntry 3 }

fanModule6StateLEDColor    OBJECT-TYPE
    SYNTAX    INTEGER {
    blue (1),green (2),red (3),amber (4),unknown (5)
    }
    MAX-ACCESS    read-only
    STATUS    current
    DESCRIPTION    "This shows the color of LED of fan module6."
    ::= { fanModule6StateLEDEntry 4 }

FanModule6StateLEDEntry ::= SEQUENCE {
    fanModule6StateLEDIndex
        Integer32,
    fanModule6StateLEDName
        DisplayString,
    fanModule6StateLEDState
        INTEGER,
    fanModule6StateLEDColor
        INTEGER
}

fanModule6StateFanTable    OBJECT-TYPE
    SYNTAX SEQUENCE OF fanModule6StateFanEntry
    MAX-ACCESS not-accessible
    STATUS     current
    DESCRIPTION "This shows the table of fan of fan module6."
    ::= { fanModule6State 10 }

fanModule6StateFanEntry    OBJECT-TYPE
    SYNTAX FanModule6StateFanEntry
    MAX-ACCESS not-accessible
    STATUS    current
    DESCRIPTION "This shows the entry of fan of fan module6."
    INDEX { fanModule6StateFanIndex }
    ::= { fanModule6StateFanTable 1 }

fanModule6StateFanIndex    OBJECT-TYPE
    SYNTAX    Integer32
    MAX-ACCESS    read-only
    STATUS    current
    DESCRIPTION    "This shows the index of fan of fan module6."
    ::= { fanModule6StateFanEntry 1 }

fanModule6StateFanLocation    OBJECT-TYPE
    SYNTAX    DisplayString (SIZE(0..40))
    MAX-ACCESS    read-only
    STATUS    current
    DESCRIPTION    "This shows the location of fan of fan module6."
    ::= { fanModule6StateFanEntry 2 }

fanModule6StateFanRPM    OBJECT-TYPE
    SYNTAX    Integer32
    UNITS    "rpm"
    MAX-ACCESS    read-only
    STATUS    current
    DESCRIPTION    "This shows the rpm value of fan module6."
    ::= { fanModule6StateFanEntry 3 }

fanModule6StateFanRPMValid    OBJECT-TYPE
    SYNTAX    INTEGER {
    invalid(1), valid(2) ,unknown(3)
    }
    MAX-ACCESS    read-only
    STATUS    current
    DESCRIPTION    "This shows the validity of fan rpm value of fan module6."
    ::= { fanModule6StateFanEntry 4 }

FanModule6StateFanEntry ::= SEQUENCE {
    fanModule6StateFanIndex
        Integer32,
    fanModule6StateFanLocation
        DisplayString,
    fanModule6StateFanRPM
        Integer32,
    fanModule6StateFanRPMValid
        INTEGER
}

powerSupply    OBJECT IDENTIFIER ::= { component 5 } 

powerSupply1    OBJECT IDENTIFIER ::= { powerSupply 1 } 

powerSupply1BasicInfo    OBJECT IDENTIFIER ::= { powerSupply1 1 } 

powerSupply1InfoProductName    OBJECT-TYPE
    SYNTAX    DisplayString (SIZE(0..40))
    MAX-ACCESS    read-only
    STATUS    current
    DESCRIPTION    "This shows the product name of power supply module1."
    ::= { powerSupply1BasicInfo 2 }

powerSupply1InfoModel    OBJECT-TYPE
    SYNTAX    DisplayString (SIZE(0..40))
    MAX-ACCESS    read-only
    STATUS    current
    DESCRIPTION    "This shows the model name of power supply module1."
    ::= { powerSupply1BasicInfo 3 }

powerSupply1InfoSerialNum    OBJECT-TYPE
    SYNTAX    DisplayString (SIZE(0..40))
    MAX-ACCESS    read-only
    STATUS    current
    DESCRIPTION    "This shows the serial number of power supply module1."
    ::= { powerSupply1BasicInfo 4 }

powerSupply1InfoProductVersion    OBJECT-TYPE
    SYNTAX    DisplayString (SIZE(0..40))
    MAX-ACCESS    read-only
    STATUS    current
    DESCRIPTION    "This shows the product version of power supply module1."
    ::= { powerSupply1BasicInfo 5 }

powerSupply1InfoProductManufacturer    OBJECT-TYPE
    SYNTAX    DisplayString (SIZE(0..40))
    MAX-ACCESS    read-only
    STATUS    current
    DESCRIPTION    "This shows the product manufacturer of power supply module1."
    ::= { powerSupply1BasicInfo 6 }

powerSupply1InfoSpec    OBJECT IDENTIFIER ::= { powerSupply1BasicInfo 20 } 

powerSupply1SpecPowerConsumption    OBJECT-TYPE
    SYNTAX    Integer32
    UNITS    "W"
    MAX-ACCESS    read-only
    STATUS    current
    DESCRIPTION    "This shows the power consumption of power supply module1."
    ::= { powerSupply1InfoSpec 1 }

powerSupply1SpecMass    OBJECT-TYPE
    SYNTAX    Integer32
    UNITS    "0.1 kg"
    MAX-ACCESS    read-only
    STATUS    current
    DESCRIPTION    "This shows the weight of power supply module1."
    ::= { powerSupply1InfoSpec 2 }

powerSupply1SpecRateVoltageMain    OBJECT-TYPE
    SYNTAX    Integer32
    UNITS    "0.1 V"
    MAX-ACCESS    read-only
    STATUS    current
    DESCRIPTION    "This shows the rated voltage of power supply module1.(main)"
    ::= { powerSupply1InfoSpec 3 }

powerSupply1SpecRateVoltageSub    OBJECT-TYPE
    SYNTAX    Integer32
    UNITS    "0.1 V"
    MAX-ACCESS    read-only
    STATUS    current
    DESCRIPTION    "This shows the rated voltage of power supply module1.(sub)"
    ::= { powerSupply1InfoSpec 4 }

powerSupply1SpecAmbientTempUpperLimit    OBJECT-TYPE
    SYNTAX    Integer32
    UNITS    "0.1 degrees C"
    MAX-ACCESS    read-only
    STATUS    current
    DESCRIPTION    "This shows the maximum limited of environment temperature of power supply module1."
    ::= { powerSupply1InfoSpec 5 }

powerSupply1SpecAmbientTempLowerLimit    OBJECT-TYPE
    SYNTAX    Integer32
    UNITS    "0.1 degrees C"
    MAX-ACCESS    read-only
    STATUS    current
    DESCRIPTION    "This shows the minimum limited of environment temperature of power supply module1."
    ::= { powerSupply1InfoSpec 6 }

powerSupply1SpecHotSpotTempUpperLimit    OBJECT-TYPE
    SYNTAX    Integer32
    UNITS    "0.1 degrees C"
    MAX-ACCESS    read-only
    STATUS    current
    DESCRIPTION    "This shows the maximum limited of hot spot temperature of power supply module1."
    ::= { powerSupply1InfoSpec 7 }

powerSupply1SpecHotSpotTempLowerLimit    OBJECT-TYPE
    SYNTAX    Integer32
    UNITS    "0.1 degrees C"
    MAX-ACCESS    read-only
    STATUS    current
    DESCRIPTION    "This shows the minimum limited of hot spot temperature of power supply module1."
    ::= { powerSupply1InfoSpec 8 }

powerSupply1SpecExhaustTempUpperLimit    OBJECT-TYPE
    SYNTAX    Integer32
    UNITS    "0.1 degrees C"
    MAX-ACCESS    read-only
    STATUS    current
    DESCRIPTION    "This shows the upper limited of exhaust temperature of power supply module1."
    ::= { powerSupply1InfoSpec 9 }

powerSupply1SpecExhaustTempLowerLimit    OBJECT-TYPE
    SYNTAX    Integer32
    UNITS    "0.1 degrees C"
    MAX-ACCESS    read-only
    STATUS    current
    DESCRIPTION    "This shows the lower limited of exhoust temperature of power supply module1."
    ::= { powerSupply1InfoSpec 10 }

powerSupply1Capacity    OBJECT IDENTIFIER ::= { powerSupply1 2 } 

powerSupply1CapacityFan    OBJECT-TYPE
    SYNTAX    Integer32
    MAX-ACCESS    read-only
    STATUS    current
    DESCRIPTION    "This shows the capacity fans of power supply module1."
    ::= { powerSupply1Capacity 1 }

powerSupply1State    OBJECT IDENTIFIER ::= { powerSupply1 4 } 

powerSupply1StateSlotNum    OBJECT-TYPE
    SYNTAX    Integer32
    MAX-ACCESS    read-only
    STATUS    current
    DESCRIPTION    "This shows the number of installed slots of power supply module1."
    ::= { powerSupply1State 1 }

powerSupply1StatePower    OBJECT-TYPE
    SYNTAX    INTEGER {
    poweroff (1), poweron (2), unknown (3)
    }
    MAX-ACCESS    read-only
    STATUS    current
    DESCRIPTION    "This shows the power supply state of power supply module1."
    ::= { powerSupply1State 2 }

powerSupply1StateHealth    OBJECT-TYPE
    SYNTAX    INTEGER {
    normal(1), fail(2) , unknown(3)
    }
    MAX-ACCESS    read-only
    STATUS    current
    DESCRIPTION    "This shows the health state of power supply module1."
    ::= { powerSupply1State 3 }

powerSupply1StateAmbientTemp    OBJECT-TYPE
    SYNTAX    Integer32
    UNITS    "0.1 degrees C"
    MAX-ACCESS    read-only
    STATUS    current
    DESCRIPTION    "This shows the temperature value of ambient sensor of power supply module1."
    ::= { powerSupply1State 4 }

powerSupply1StateHotSpotTemp    OBJECT-TYPE
    SYNTAX    Integer32
    UNITS    "0.1 degrees C"
    MAX-ACCESS    read-only
    STATUS    current
    DESCRIPTION    "This shows the temperature value of hot spot sensor of power supply module1."
    ::= { powerSupply1State 5 }

powerSupply1StateExhaustTemp    OBJECT-TYPE
    SYNTAX    Integer32
    UNITS    "0.1 degrees C"
    MAX-ACCESS    read-only
    STATUS    current
    DESCRIPTION    "This shows the temperature value of exhaust sensor of power supply module."
    ::= { powerSupply1State 6 }

powerSupply1StateMainVoltage    OBJECT-TYPE
    SYNTAX    Integer32
    UNITS    "0.1 V"
    MAX-ACCESS    read-only
    STATUS    current
    DESCRIPTION    "This shows the main voltage of power supply module1."
    ::= { powerSupply1State 7 }

powerSupply1StateSubVoltage    OBJECT-TYPE
    SYNTAX    Integer32
    UNITS    "0.1 V"
    MAX-ACCESS    read-only
    STATUS    current
    DESCRIPTION    "This shows the sub voltage of power supply module1."
    ::= { powerSupply1State 8 }

powerSupply1StateInputVoltage    OBJECT-TYPE
    SYNTAX    Integer32
    UNITS    "0.1 V"
    MAX-ACCESS    read-only
    STATUS    current
    DESCRIPTION    "This shows the input voltage of power supply module1."
    ::= { powerSupply1State 9 }

powerSupply1StateMainCurrent    OBJECT-TYPE
    SYNTAX    Integer32
    UNITS    "0.1 A"
    MAX-ACCESS    read-only
    STATUS    current
    DESCRIPTION    "This shows the main current of power supply module1."
    ::= { powerSupply1State 10 }

powerSupply1StateSubCurrent    OBJECT-TYPE
    SYNTAX    Integer32
    UNITS    "0.1 A"
    MAX-ACCESS    read-only
    STATUS    current
    DESCRIPTION    "This shows the sub current of power supply module1."
    ::= { powerSupply1State 11 }

powerSupply1StateInputCurrent    OBJECT-TYPE
    SYNTAX    Integer32
    UNITS    "0.1 A"
    MAX-ACCESS    read-only
    STATUS    current
    DESCRIPTION    "This shows the input current of power supply module1."
    ::= { powerSupply1State 12 }

powerSupply1StateFanTable    OBJECT-TYPE
    SYNTAX SEQUENCE OF powerSupply1StateFanEntry
    MAX-ACCESS not-accessible
    STATUS     current
    DESCRIPTION "This shows the table of fan of power supply module1."
    ::= { powerSupply1State 14 }

powerSupply1StateFanEntry    OBJECT-TYPE
    SYNTAX PowerSupply1StateFanEntry
    MAX-ACCESS not-accessible
    STATUS    current
    DESCRIPTION "This shows the entry of fan of power supply module1."
    INDEX { powerSupply1StateFanIndex }
    ::= { powerSupply1StateFanTable 1 }

powerSupply1StateFanIndex    OBJECT-TYPE
    SYNTAX    Integer32
    MAX-ACCESS    read-only
    STATUS    current
    DESCRIPTION    "This shows the index of fan of power supply module1."
    ::= { powerSupply1StateFanEntry 1 }

powerSupply1StateFanLocation    OBJECT-TYPE
    SYNTAX    DisplayString (SIZE(0..40))
    MAX-ACCESS    read-only
    STATUS    current
    DESCRIPTION    "This shows the location of fan of power supply module1."
    ::= { powerSupply1StateFanEntry 2 }

powerSupply1StateFanRPM    OBJECT-TYPE
    SYNTAX    Integer32
    UNITS    "rpm"
    MAX-ACCESS    read-only
    STATUS    current
    DESCRIPTION    "This shows the rpm value of fan of power supply module1."
    ::= { powerSupply1StateFanEntry 3 }

PowerSupply1StateFanEntry ::= SEQUENCE {
    powerSupply1StateFanIndex
        Integer32,
    powerSupply1StateFanLocation
        DisplayString,
    powerSupply1StateFanRPM
        Integer32
}

powerSupply2    OBJECT IDENTIFIER ::= { powerSupply 2 } 

powerSupply2BasicInfo    OBJECT IDENTIFIER ::= { powerSupply2 1 } 

powerSupply2InfoProductName    OBJECT-TYPE
    SYNTAX    DisplayString (SIZE(0..40))
    MAX-ACCESS    read-only
    STATUS    current
    DESCRIPTION    "This shows the product name of power supply module2."
    ::= { powerSupply2BasicInfo 2 }

powerSupply2InfoModel    OBJECT-TYPE
    SYNTAX    DisplayString (SIZE(0..40))
    MAX-ACCESS    read-only
    STATUS    current
    DESCRIPTION    "This shows the model name of power supply module2."
    ::= { powerSupply2BasicInfo 3 }

powerSupply2InfoSerialNum    OBJECT-TYPE
    SYNTAX    DisplayString (SIZE(0..40))
    MAX-ACCESS    read-only
    STATUS    current
    DESCRIPTION    "This shows the serial number of power supply module2."
    ::= { powerSupply2BasicInfo 4 }

powerSupply2InfoProductVersion    OBJECT-TYPE
    SYNTAX    DisplayString (SIZE(0..40))
    MAX-ACCESS    read-only
    STATUS    current
    DESCRIPTION    "This shows the product version of power supply module2."
    ::= { powerSupply2BasicInfo 5 }

powerSupply2InfoProductManufacturer    OBJECT-TYPE
    SYNTAX    DisplayString (SIZE(0..40))
    MAX-ACCESS    read-only
    STATUS    current
    DESCRIPTION    "This shows the product manufacturer of power supply module2."
    ::= { powerSupply2BasicInfo 6 }

powerSupply2InfoSpec    OBJECT IDENTIFIER ::= { powerSupply2BasicInfo 20 } 

powerSupply2SpecPowerConsumption    OBJECT-TYPE
    SYNTAX    Integer32
    UNITS    "W"
    MAX-ACCESS    read-only
    STATUS    current
    DESCRIPTION    "This shows the power consumption of power supply module2."
    ::= { powerSupply2InfoSpec 1 }

powerSupply2SpecMass    OBJECT-TYPE
    SYNTAX    Integer32
    UNITS    "0.1 kg"
    MAX-ACCESS    read-only
    STATUS    current
    DESCRIPTION    "This shows the weight of power supply module2."
    ::= { powerSupply2InfoSpec 2 }

powerSupply2SpecRateVoltageMain    OBJECT-TYPE
    SYNTAX    Integer32
    UNITS    "0.1 V"
    MAX-ACCESS    read-only
    STATUS    current
    DESCRIPTION    "This shows the rated voltage of power supply module2.(main)"
    ::= { powerSupply2InfoSpec 3 }

powerSupply2SpecRateVoltageSub    OBJECT-TYPE
    SYNTAX    Integer32
    UNITS    "0.1 V"
    MAX-ACCESS    read-only
    STATUS    current
    DESCRIPTION    "This shows the rated voltage of power supply module2.(sub)"
    ::= { powerSupply2InfoSpec 4 }

powerSupply2SpecAmbientTempUpperLimit    OBJECT-TYPE
    SYNTAX    Integer32
    UNITS    "0.1 degrees C"
    MAX-ACCESS    read-only
    STATUS    current
    DESCRIPTION    "This shows the maximum limited of environment temperature of power supply module2."
    ::= { powerSupply2InfoSpec 5 }

powerSupply2SpecAmbientTempLowerLimit    OBJECT-TYPE
    SYNTAX    Integer32
    UNITS    "0.1 degrees C"
    MAX-ACCESS    read-only
    STATUS    current
    DESCRIPTION    "This shows the minimum limited of environment temperature of power supply module2."
    ::= { powerSupply2InfoSpec 6 }

powerSupply2SpecHotSpotTempUpperLimit    OBJECT-TYPE
    SYNTAX    Integer32
    UNITS    "0.1 degrees C"
    MAX-ACCESS    read-only
    STATUS    current
    DESCRIPTION    "This shows the maximum limited of hot spot temperature of power supply module2."
    ::= { powerSupply2InfoSpec 7 }

powerSupply2SpecHotSpotTempLowerLimit    OBJECT-TYPE
    SYNTAX    Integer32
    UNITS    "0.1 degrees C"
    MAX-ACCESS    read-only
    STATUS    current
    DESCRIPTION    "This shows the minimum limited of hot spot temperature of power supply module2."
    ::= { powerSupply2InfoSpec 8 }

powerSupply2SpecExhaustTempUpperLimit    OBJECT-TYPE
    SYNTAX    Integer32
    UNITS    "0.1 degrees C"
    MAX-ACCESS    read-only
    STATUS    current
    DESCRIPTION    "This shows the upper limited of exhaust temperature of power supply module2."
    ::= { powerSupply2InfoSpec 9 }

powerSupply2SpecExhaustTempLowerLimit    OBJECT-TYPE
    SYNTAX    Integer32
    UNITS    "0.1 degrees C"
    MAX-ACCESS    read-only
    STATUS    current
    DESCRIPTION    "This shows the lower limited of exhoust temperature of power supply module2."
    ::= { powerSupply2InfoSpec 10 }

powerSupply2Capacity    OBJECT IDENTIFIER ::= { powerSupply2 2 } 

powerSupply2CapacityFan    OBJECT-TYPE
    SYNTAX    Integer32
    MAX-ACCESS    read-only
    STATUS    current
    DESCRIPTION    "This shows the capacity fans of power supply module2."
    ::= { powerSupply2Capacity 1 }

powerSupply2State    OBJECT IDENTIFIER ::= { powerSupply2 4 } 

powerSupply2StateSlotNum    OBJECT-TYPE
    SYNTAX    Integer32
    MAX-ACCESS    read-only
    STATUS    current
    DESCRIPTION    "This shows the number of installed slots of power supply module2."
    ::= { powerSupply2State 1 }

powerSupply2StatePower    OBJECT-TYPE
    SYNTAX    INTEGER {
    poweroff (1), poweron (2), unknown (3)
    }
    MAX-ACCESS    read-only
    STATUS    current
    DESCRIPTION    "This shows the power supply state of power supply module2."
    ::= { powerSupply2State 2 }

powerSupply2StateHealth    OBJECT-TYPE
    SYNTAX    INTEGER {
    normal(1), fail(2) , unknown(3)
    }
    MAX-ACCESS    read-only
    STATUS    current
    DESCRIPTION    "This shows the health state of power supply module2."
    ::= { powerSupply2State 3 }

powerSupply2StateAmbientTemp    OBJECT-TYPE
    SYNTAX    Integer32
    UNITS    "0.1 degrees C"
    MAX-ACCESS    read-only
    STATUS    current
    DESCRIPTION    "This shows the temperature value of ambient sensor of power supply module2."
    ::= { powerSupply2State 4 }

powerSupply2StateHotSpotTemp    OBJECT-TYPE
    SYNTAX    Integer32
    UNITS    "0.1 degrees C"
    MAX-ACCESS    read-only
    STATUS    current
    DESCRIPTION    "This shows the temperature value of hot spot sensor of power supply module2."
    ::= { powerSupply2State 5 }

powerSupply2StateExhaustTemp    OBJECT-TYPE
    SYNTAX    Integer32
    UNITS    "0.1 degrees C"
    MAX-ACCESS    read-only
    STATUS    current
    DESCRIPTION    "This shows the temperature value of exhaust sensor of power supply module."
    ::= { powerSupply2State 6 }

powerSupply2StateMainVoltage    OBJECT-TYPE
    SYNTAX    Integer32
    UNITS    "0.1 V"
    MAX-ACCESS    read-only
    STATUS    current
    DESCRIPTION    "This shows the main voltage of power supply module2."
    ::= { powerSupply2State 7 }

powerSupply2StateSubVoltage    OBJECT-TYPE
    SYNTAX    Integer32
    UNITS    "0.1 V"
    MAX-ACCESS    read-only
    STATUS    current
    DESCRIPTION    "This shows the sub voltage of power supply module2."
    ::= { powerSupply2State 8 }

powerSupply2StateInputVoltage    OBJECT-TYPE
    SYNTAX    Integer32
    UNITS    "0.1 V"
    MAX-ACCESS    read-only
    STATUS    current
    DESCRIPTION    "This shows the input voltage of power supply module2."
    ::= { powerSupply2State 9 }

powerSupply2StateMainCurrent    OBJECT-TYPE
    SYNTAX    Integer32
    UNITS    "0.1 A"
    MAX-ACCESS    read-only
    STATUS    current
    DESCRIPTION    "This shows the main current of power supply module2."
    ::= { powerSupply2State 10 }

powerSupply2StateSubCurrent    OBJECT-TYPE
    SYNTAX    Integer32
    UNITS    "0.1 A"
    MAX-ACCESS    read-only
    STATUS    current
    DESCRIPTION    "This shows the sub current of power supply module2."
    ::= { powerSupply2State 11 }

powerSupply2StateInputCurrent    OBJECT-TYPE
    SYNTAX    Integer32
    UNITS    "0.1 A"
    MAX-ACCESS    read-only
    STATUS    current
    DESCRIPTION    "This shows the input current of power supply module2."
    ::= { powerSupply2State 12 }

powerSupply2StateFanTable    OBJECT-TYPE
    SYNTAX SEQUENCE OF powerSupply2StateFanEntry
    MAX-ACCESS not-accessible
    STATUS     current
    DESCRIPTION "This shows the table of fan of power supply module2."
    ::= { powerSupply2State 14 }

powerSupply2StateFanEntry    OBJECT-TYPE
    SYNTAX PowerSupply2StateFanEntry
    MAX-ACCESS not-accessible
    STATUS    current
    DESCRIPTION "This shows the entry of fan of power supply module2."
    INDEX { powerSupply2StateFanIndex }
    ::= { powerSupply2StateFanTable 1 }

powerSupply2StateFanIndex    OBJECT-TYPE
    SYNTAX    Integer32
    MAX-ACCESS    read-only
    STATUS    current
    DESCRIPTION    "This shows the index of fan of power supply module2."
    ::= { powerSupply2StateFanEntry 1 }

powerSupply2StateFanLocation    OBJECT-TYPE
    SYNTAX    DisplayString (SIZE(0..40))
    MAX-ACCESS    read-only
    STATUS    current
    DESCRIPTION    "This shows the location of fan of power supply module2."
    ::= { powerSupply2StateFanEntry 2 }

powerSupply2StateFanRPM    OBJECT-TYPE
    SYNTAX    Integer32
    UNITS    "rpm"
    MAX-ACCESS    read-only
    STATUS    current
    DESCRIPTION    "This shows the rpm value of fan of power supply module2."
    ::= { powerSupply2StateFanEntry 3 }

PowerSupply2StateFanEntry ::= SEQUENCE {
    powerSupply2StateFanIndex
        Integer32,
    powerSupply2StateFanLocation
        DisplayString,
    powerSupply2StateFanRPM
        Integer32
}

powerSupply3    OBJECT IDENTIFIER ::= { powerSupply 3 } 

powerSupply3BasicInfo    OBJECT IDENTIFIER ::= { powerSupply3 1 } 

powerSupply3InfoProductName    OBJECT-TYPE
    SYNTAX    DisplayString (SIZE(0..40))
    MAX-ACCESS    read-only
    STATUS    current
    DESCRIPTION    "This shows the product name of power supply module3."
    ::= { powerSupply3BasicInfo 2 }

powerSupply3InfoModel    OBJECT-TYPE
    SYNTAX    DisplayString (SIZE(0..40))
    MAX-ACCESS    read-only
    STATUS    current
    DESCRIPTION    "This shows the model name of power supply module3."
    ::= { powerSupply3BasicInfo 3 }

powerSupply3InfoSerialNum    OBJECT-TYPE
    SYNTAX    DisplayString (SIZE(0..40))
    MAX-ACCESS    read-only
    STATUS    current
    DESCRIPTION    "This shows the serial number of power supply module3."
    ::= { powerSupply3BasicInfo 4 }

powerSupply3InfoProductVersion    OBJECT-TYPE
    SYNTAX    DisplayString (SIZE(0..40))
    MAX-ACCESS    read-only
    STATUS    current
    DESCRIPTION    "This shows the product version of power supply module3."
    ::= { powerSupply3BasicInfo 5 }

powerSupply3InfoProductManufacturer    OBJECT-TYPE
    SYNTAX    DisplayString (SIZE(0..40))
    MAX-ACCESS    read-only
    STATUS    current
    DESCRIPTION    "This shows the product manufacturer of power supply module3."
    ::= { powerSupply3BasicInfo 6 }

powerSupply3InfoSpec    OBJECT IDENTIFIER ::= { powerSupply3BasicInfo 20 } 

powerSupply3SpecPowerConsumption    OBJECT-TYPE
    SYNTAX    Integer32
    UNITS    "W"
    MAX-ACCESS    read-only
    STATUS    current
    DESCRIPTION    "This shows the power consumption of power supply module3."
    ::= { powerSupply3InfoSpec 1 }

powerSupply3SpecMass    OBJECT-TYPE
    SYNTAX    Integer32
    UNITS    "0.1 kg"
    MAX-ACCESS    read-only
    STATUS    current
    DESCRIPTION    "This shows the weight of power supply module3."
    ::= { powerSupply3InfoSpec 2 }

powerSupply3SpecRateVoltageMain    OBJECT-TYPE
    SYNTAX    Integer32
    UNITS    "0.1 V"
    MAX-ACCESS    read-only
    STATUS    current
    DESCRIPTION    "This shows the rated voltage of power supply module3.(main)"
    ::= { powerSupply3InfoSpec 3 }

powerSupply3SpecRateVoltageSub    OBJECT-TYPE
    SYNTAX    Integer32
    UNITS    "0.1 V"
    MAX-ACCESS    read-only
    STATUS    current
    DESCRIPTION    "This shows the rated voltage of power supply module3.(sub)"
    ::= { powerSupply3InfoSpec 4 }

powerSupply3SpecAmbientTempUpperLimit    OBJECT-TYPE
    SYNTAX    Integer32
    UNITS    "0.1 degrees C"
    MAX-ACCESS    read-only
    STATUS    current
    DESCRIPTION    "This shows the maximum limited of environment temperature of power supply module3."
    ::= { powerSupply3InfoSpec 5 }

powerSupply3SpecAmbientTempLowerLimit    OBJECT-TYPE
    SYNTAX    Integer32
    UNITS    "0.1 degrees C"
    MAX-ACCESS    read-only
    STATUS    current
    DESCRIPTION    "This shows the minimum limited of environment temperature of power supply module3."
    ::= { powerSupply3InfoSpec 6 }

powerSupply3SpecHotSpotTempUpperLimit    OBJECT-TYPE
    SYNTAX    Integer32
    UNITS    "0.1 degrees C"
    MAX-ACCESS    read-only
    STATUS    current
    DESCRIPTION    "This shows the maximum limited of hot spot temperature of power supply module3."
    ::= { powerSupply3InfoSpec 7 }

powerSupply3SpecHotSpotTempLowerLimit    OBJECT-TYPE
    SYNTAX    Integer32
    UNITS    "0.1 degrees C"
    MAX-ACCESS    read-only
    STATUS    current
    DESCRIPTION    "This shows the minimum limited of hot spot temperature of power supply module3."
    ::= { powerSupply3InfoSpec 8 }

powerSupply3SpecExhaustTempUpperLimit    OBJECT-TYPE
    SYNTAX    Integer32
    UNITS    "0.1 degrees C"
    MAX-ACCESS    read-only
    STATUS    current
    DESCRIPTION    "This shows the upper limited of exhaust temperature of power supply module3."
    ::= { powerSupply3InfoSpec 9 }

powerSupply3SpecExhaustTempLowerLimit    OBJECT-TYPE
    SYNTAX    Integer32
    UNITS    "0.1 degrees C"
    MAX-ACCESS    read-only
    STATUS    current
    DESCRIPTION    "This shows the lower limited of exhoust temperature of power supply module3."
    ::= { powerSupply3InfoSpec 10 }

powerSupply3Capacity    OBJECT IDENTIFIER ::= { powerSupply3 2 } 

powerSupply3CapacityFan    OBJECT-TYPE
    SYNTAX    Integer32
    MAX-ACCESS    read-only
    STATUS    current
    DESCRIPTION    "This shows the capacity fans of power supply module3."
    ::= { powerSupply3Capacity 1 }

powerSupply3State    OBJECT IDENTIFIER ::= { powerSupply3 4 } 

powerSupply3StateSlotNum    OBJECT-TYPE
    SYNTAX    Integer32
    MAX-ACCESS    read-only
    STATUS    current
    DESCRIPTION    "This shows the number of installed slots of power supply module3."
    ::= { powerSupply3State 1 }

powerSupply3StatePower    OBJECT-TYPE
    SYNTAX    INTEGER {
    poweroff (1), poweron (2), unknown (3)
    }
    MAX-ACCESS    read-only
    STATUS    current
    DESCRIPTION    "This shows the power supply state of power supply module3."
    ::= { powerSupply3State 2 }

powerSupply3StateHealth    OBJECT-TYPE
    SYNTAX    INTEGER {
    normal(1), fail(2) , unknown(3)
    }
    MAX-ACCESS    read-only
    STATUS    current
    DESCRIPTION    "This shows the health state of power supply module3."
    ::= { powerSupply3State 3 }

powerSupply3StateAmbientTemp    OBJECT-TYPE
    SYNTAX    Integer32
    UNITS    "0.1 degrees C"
    MAX-ACCESS    read-only
    STATUS    current
    DESCRIPTION    "This shows the temperature value of ambient sensor of power supply module3."
    ::= { powerSupply3State 4 }

powerSupply3StateHotSpotTemp    OBJECT-TYPE
    SYNTAX    Integer32
    UNITS    "0.1 degrees C"
    MAX-ACCESS    read-only
    STATUS    current
    DESCRIPTION    "This shows the temperature value of hot spot sensor of power supply module3."
    ::= { powerSupply3State 5 }

powerSupply3StateExhaustTemp    OBJECT-TYPE
    SYNTAX    Integer32
    UNITS    "0.1 degrees C"
    MAX-ACCESS    read-only
    STATUS    current
    DESCRIPTION    "This shows the temperature value of exhaust sensor of power supply module."
    ::= { powerSupply3State 6 }

powerSupply3StateMainVoltage    OBJECT-TYPE
    SYNTAX    Integer32
    UNITS    "0.1 V"
    MAX-ACCESS    read-only
    STATUS    current
    DESCRIPTION    "This shows the main voltage of power supply module3."
    ::= { powerSupply3State 7 }

powerSupply3StateSubVoltage    OBJECT-TYPE
    SYNTAX    Integer32
    UNITS    "0.1 V"
    MAX-ACCESS    read-only
    STATUS    current
    DESCRIPTION    "This shows the sub voltage of power supply module3."
    ::= { powerSupply3State 8 }

powerSupply3StateInputVoltage    OBJECT-TYPE
    SYNTAX    Integer32
    UNITS    "0.1 V"
    MAX-ACCESS    read-only
    STATUS    current
    DESCRIPTION    "This shows the input voltage of power supply module3."
    ::= { powerSupply3State 9 }

powerSupply3StateMainCurrent    OBJECT-TYPE
    SYNTAX    Integer32
    UNITS    "0.1 A"
    MAX-ACCESS    read-only
    STATUS    current
    DESCRIPTION    "This shows the main current of power supply module3."
    ::= { powerSupply3State 10 }

powerSupply3StateSubCurrent    OBJECT-TYPE
    SYNTAX    Integer32
    UNITS    "0.1 A"
    MAX-ACCESS    read-only
    STATUS    current
    DESCRIPTION    "This shows the sub current of power supply module3."
    ::= { powerSupply3State 11 }

powerSupply3StateInputCurrent    OBJECT-TYPE
    SYNTAX    Integer32
    UNITS    "0.1 A"
    MAX-ACCESS    read-only
    STATUS    current
    DESCRIPTION    "This shows the input current of power supply module3."
    ::= { powerSupply3State 12 }

powerSupply3StateFanTable    OBJECT-TYPE
    SYNTAX SEQUENCE OF powerSupply3StateFanEntry
    MAX-ACCESS not-accessible
    STATUS     current
    DESCRIPTION "This shows the table of fan of power supply module3."
    ::= { powerSupply3State 14 }

powerSupply3StateFanEntry    OBJECT-TYPE
    SYNTAX PowerSupply3StateFanEntry
    MAX-ACCESS not-accessible
    STATUS    current
    DESCRIPTION "This shows the entry of fan of power supply module3."
    INDEX { powerSupply3StateFanIndex }
    ::= { powerSupply3StateFanTable 1 }

powerSupply3StateFanIndex    OBJECT-TYPE
    SYNTAX    Integer32
    MAX-ACCESS    read-only
    STATUS    current
    DESCRIPTION    "This shows the index of fan of power supply module3."
    ::= { powerSupply3StateFanEntry 1 }

powerSupply3StateFanLocation    OBJECT-TYPE
    SYNTAX    DisplayString (SIZE(0..40))
    MAX-ACCESS    read-only
    STATUS    current
    DESCRIPTION    "This shows the location of fan of power supply module3."
    ::= { powerSupply3StateFanEntry 2 }

powerSupply3StateFanRPM    OBJECT-TYPE
    SYNTAX    Integer32
    UNITS    "rpm"
    MAX-ACCESS    read-only
    STATUS    current
    DESCRIPTION    "This shows the rpm value of fan of power supply module3."
    ::= { powerSupply3StateFanEntry 3 }

PowerSupply3StateFanEntry ::= SEQUENCE {
    powerSupply3StateFanIndex
        Integer32,
    powerSupply3StateFanLocation
        DisplayString,
    powerSupply3StateFanRPM
        Integer32
}

powerSupply4    OBJECT IDENTIFIER ::= { powerSupply 4 } 

powerSupply4BasicInfo    OBJECT IDENTIFIER ::= { powerSupply4 1 } 

powerSupply4InfoProductName    OBJECT-TYPE
    SYNTAX    DisplayString (SIZE(0..40))
    MAX-ACCESS    read-only
    STATUS    current
    DESCRIPTION    "This shows the product name of power supply module4."
    ::= { powerSupply4BasicInfo 2 }

powerSupply4InfoModel    OBJECT-TYPE
    SYNTAX    DisplayString (SIZE(0..40))
    MAX-ACCESS    read-only
    STATUS    current
    DESCRIPTION    "This shows the model name of power supply module4."
    ::= { powerSupply4BasicInfo 3 }

powerSupply4InfoSerialNum    OBJECT-TYPE
    SYNTAX    DisplayString (SIZE(0..40))
    MAX-ACCESS    read-only
    STATUS    current
    DESCRIPTION    "This shows the serial number of power supply module4."
    ::= { powerSupply4BasicInfo 4 }

powerSupply4InfoProductVersion    OBJECT-TYPE
    SYNTAX    DisplayString (SIZE(0..40))
    MAX-ACCESS    read-only
    STATUS    current
    DESCRIPTION    "This shows the product version of power supply module4."
    ::= { powerSupply4BasicInfo 5 }

powerSupply4InfoProductManufacturer    OBJECT-TYPE
    SYNTAX    DisplayString (SIZE(0..40))
    MAX-ACCESS    read-only
    STATUS    current
    DESCRIPTION    "This shows the product manufacturer of power supply module4."
    ::= { powerSupply4BasicInfo 6 }

powerSupply4InfoSpec    OBJECT IDENTIFIER ::= { powerSupply4BasicInfo 20 } 

powerSupply4SpecPowerConsumption    OBJECT-TYPE
    SYNTAX    Integer32
    UNITS    "W"
    MAX-ACCESS    read-only
    STATUS    current
    DESCRIPTION    "This shows the power consumption of power supply module4."
    ::= { powerSupply4InfoSpec 1 }

powerSupply4SpecMass    OBJECT-TYPE
    SYNTAX    Integer32
    UNITS    "0.1 kg"
    MAX-ACCESS    read-only
    STATUS    current
    DESCRIPTION    "This shows the weight of power supply module4."
    ::= { powerSupply4InfoSpec 2 }

powerSupply4SpecRateVoltageMain    OBJECT-TYPE
    SYNTAX    Integer32
    UNITS    "0.1 V"
    MAX-ACCESS    read-only
    STATUS    current
    DESCRIPTION    "This shows the rated voltage of power supply module4.(main)"
    ::= { powerSupply4InfoSpec 3 }

powerSupply4SpecRateVoltageSub    OBJECT-TYPE
    SYNTAX    Integer32
    UNITS    "0.1 V"
    MAX-ACCESS    read-only
    STATUS    current
    DESCRIPTION    "This shows the rated voltage of power supply module4.(sub)"
    ::= { powerSupply4InfoSpec 4 }

powerSupply4SpecAmbientTempUpperLimit    OBJECT-TYPE
    SYNTAX    Integer32
    UNITS    "0.1 degrees C"
    MAX-ACCESS    read-only
    STATUS    current
    DESCRIPTION    "This shows the maximum limited of environment temperature of power supply module4."
    ::= { powerSupply4InfoSpec 5 }

powerSupply4SpecAmbientTempLowerLimit    OBJECT-TYPE
    SYNTAX    Integer32
    UNITS    "0.1 degrees C"
    MAX-ACCESS    read-only
    STATUS    current
    DESCRIPTION    "This shows the minimum limited of environment temperature of power supply module4."
    ::= { powerSupply4InfoSpec 6 }

powerSupply4SpecHotSpotTempUpperLimit    OBJECT-TYPE
    SYNTAX    Integer32
    UNITS    "0.1 degrees C"
    MAX-ACCESS    read-only
    STATUS    current
    DESCRIPTION    "This shows the maximum limited of hot spot temperature of power supply module4."
    ::= { powerSupply4InfoSpec 7 }

powerSupply4SpecHotSpotTempLowerLimit    OBJECT-TYPE
    SYNTAX    Integer32
    UNITS    "0.1 degrees C"
    MAX-ACCESS    read-only
    STATUS    current
    DESCRIPTION    "This shows the minimum limited of hot spot temperature of power supply module4."
    ::= { powerSupply4InfoSpec 8 }

powerSupply4SpecExhaustTempUpperLimit    OBJECT-TYPE
    SYNTAX    Integer32
    UNITS    "0.1 degrees C"
    MAX-ACCESS    read-only
    STATUS    current
    DESCRIPTION    "This shows the upper limited of exhaust temperature of power supply module4."
    ::= { powerSupply4InfoSpec 9 }

powerSupply4SpecExhaustTempLowerLimit    OBJECT-TYPE
    SYNTAX    Integer32
    UNITS    "0.1 degrees C"
    MAX-ACCESS    read-only
    STATUS    current
    DESCRIPTION    "This shows the lower limited of exhoust temperature of power supply module4."
    ::= { powerSupply4InfoSpec 10 }

powerSupply4Capacity    OBJECT IDENTIFIER ::= { powerSupply4 2 } 

powerSupply4CapacityFan    OBJECT-TYPE
    SYNTAX    Integer32
    MAX-ACCESS    read-only
    STATUS    current
    DESCRIPTION    "This shows the capacity fans of power supply module4."
    ::= { powerSupply4Capacity 1 }

powerSupply4State    OBJECT IDENTIFIER ::= { powerSupply4 4 } 

powerSupply4StateSlotNum    OBJECT-TYPE
    SYNTAX    Integer32
    MAX-ACCESS    read-only
    STATUS    current
    DESCRIPTION    "This shows the number of installed slots of power supply module4."
    ::= { powerSupply4State 1 }

powerSupply4StatePower    OBJECT-TYPE
    SYNTAX    INTEGER {
    poweroff (1), poweron (2), unknown (3)
    }
    MAX-ACCESS    read-only
    STATUS    current
    DESCRIPTION    "This shows the power supply state of power supply module4."
    ::= { powerSupply4State 2 }

powerSupply4StateHealth    OBJECT-TYPE
    SYNTAX    INTEGER {
    normal(1), fail(2) , unknown(3)
    }
    MAX-ACCESS    read-only
    STATUS    current
    DESCRIPTION    "This shows the health state of power supply module4."
    ::= { powerSupply4State 3 }

powerSupply4StateAmbientTemp    OBJECT-TYPE
    SYNTAX    Integer32
    UNITS    "0.1 degrees C"
    MAX-ACCESS    read-only
    STATUS    current
    DESCRIPTION    "This shows the temperature value of ambient sensor of power supply module4."
    ::= { powerSupply4State 4 }

powerSupply4StateHotSpotTemp    OBJECT-TYPE
    SYNTAX    Integer32
    UNITS    "0.1 degrees C"
    MAX-ACCESS    read-only
    STATUS    current
    DESCRIPTION    "This shows the temperature value of hot spot sensor of power supply module4."
    ::= { powerSupply4State 5 }

powerSupply4StateExhaustTemp    OBJECT-TYPE
    SYNTAX    Integer32
    UNITS    "0.1 degrees C"
    MAX-ACCESS    read-only
    STATUS    current
    DESCRIPTION    "This shows the temperature value of exhaust sensor of power supply module."
    ::= { powerSupply4State 6 }

powerSupply4StateMainVoltage    OBJECT-TYPE
    SYNTAX    Integer32
    UNITS    "0.1 V"
    MAX-ACCESS    read-only
    STATUS    current
    DESCRIPTION    "This shows the main voltage of power supply module4."
    ::= { powerSupply4State 7 }

powerSupply4StateSubVoltage    OBJECT-TYPE
    SYNTAX    Integer32
    UNITS    "0.1 V"
    MAX-ACCESS    read-only
    STATUS    current
    DESCRIPTION    "This shows the sub voltage of power supply module4."
    ::= { powerSupply4State 8 }

powerSupply4StateInputVoltage    OBJECT-TYPE
    SYNTAX    Integer32
    UNITS    "0.1 V"
    MAX-ACCESS    read-only
    STATUS    current
    DESCRIPTION    "This shows the input voltage of power supply module4."
    ::= { powerSupply4State 9 }

powerSupply4StateMainCurrent    OBJECT-TYPE
    SYNTAX    Integer32
    UNITS    "0.1 A"
    MAX-ACCESS    read-only
    STATUS    current
    DESCRIPTION    "This shows the main current of power supply module4."
    ::= { powerSupply4State 10 }

powerSupply4StateSubCurrent    OBJECT-TYPE
    SYNTAX    Integer32
    UNITS    "0.1 A"
    MAX-ACCESS    read-only
    STATUS    current
    DESCRIPTION    "This shows the sub current of power supply module4."
    ::= { powerSupply4State 11 }

powerSupply4StateInputCurrent    OBJECT-TYPE
    SYNTAX    Integer32
    UNITS    "0.1 A"
    MAX-ACCESS    read-only
    STATUS    current
    DESCRIPTION    "This shows the input current of power supply module4."
    ::= { powerSupply4State 12 }

powerSupply4StateFanTable    OBJECT-TYPE
    SYNTAX SEQUENCE OF powerSupply4StateFanEntry
    MAX-ACCESS not-accessible
    STATUS     current
    DESCRIPTION "This shows the table of fan of power supply module4."
    ::= { powerSupply4State 14 }

powerSupply4StateFanEntry    OBJECT-TYPE
    SYNTAX PowerSupply4StateFanEntry
    MAX-ACCESS not-accessible
    STATUS    current
    DESCRIPTION "This shows the entry of fan of power supply module4."
    INDEX { powerSupply4StateFanIndex }
    ::= { powerSupply4StateFanTable 1 }

powerSupply4StateFanIndex    OBJECT-TYPE
    SYNTAX    Integer32
    MAX-ACCESS    read-only
    STATUS    current
    DESCRIPTION    "This shows the index of fan of power supply module4."
    ::= { powerSupply4StateFanEntry 1 }

powerSupply4StateFanLocation    OBJECT-TYPE
    SYNTAX    DisplayString (SIZE(0..40))
    MAX-ACCESS    read-only
    STATUS    current
    DESCRIPTION    "This shows the location of fan of power supply module4."
    ::= { powerSupply4StateFanEntry 2 }

powerSupply4StateFanRPM    OBJECT-TYPE
    SYNTAX    Integer32
    UNITS    "rpm"
    MAX-ACCESS    read-only
    STATUS    current
    DESCRIPTION    "This shows the rpm value of fan of power supply module4."
    ::= { powerSupply4StateFanEntry 3 }

PowerSupply4StateFanEntry ::= SEQUENCE {
    powerSupply4StateFanIndex
        Integer32,
    powerSupply4StateFanLocation
        DisplayString,
    powerSupply4StateFanRPM
        Integer32
}

partition    OBJECT IDENTIFIER ::= { computeBlade 3 } 

partition1    OBJECT IDENTIFIER ::= { partition 1 } 

partition1BasicInfo    OBJECT IDENTIFIER ::= { partition1 1 } 

partition1Valid    OBJECT-TYPE
    SYNTAX    INTEGER {
    invalid(1), valid(2) ,unknown(3)
    }
    MAX-ACCESS    read-only
    STATUS    current
    DESCRIPTION    "This shows the validity of information of partition1."
    ::= { partition1BasicInfo 1 }

partition1MaxCurrent    OBJECT-TYPE
    SYNTAX    Integer32
    UNITS    "0.1 A"
    MAX-ACCESS    read-only
    STATUS    current
    DESCRIPTION    "This shows the maximum current of partition1."
    ::= { partition1BasicInfo 2 }

partition1MaxPower    OBJECT-TYPE
    SYNTAX    Integer32
    UNITS    "W"
    MAX-ACCESS    read-only
    STATUS    current
    DESCRIPTION    "This shows the maximum power of partition1."
    ::= { partition1BasicInfo 3 }

partition1ProcCoreCount    OBJECT-TYPE
    SYNTAX    Integer32
    MAX-ACCESS    read-only
    STATUS    current
    DESCRIPTION    "This shows the total number of CPU core of partition1."
    ::= { partition1BasicInfo 4 }

partition1DIMMCapacity    OBJECT-TYPE
    SYNTAX    Integer32
    UNITS    "GB"
    MAX-ACCESS    read-only
    STATUS    current
    DESCRIPTION    "This shows the total amount of DIMM capacity of partition1."
    ::= { partition1BasicInfo 5 }

partition1HVMLicenceModel    OBJECT-TYPE
    SYNTAX    DisplayString (SIZE(0..40))
    MAX-ACCESS    read-only
    STATUS    current
    DESCRIPTION    "This shows the HVM licence information of partition1 (model)."
    ::= { partition1BasicInfo 6 }

partition1HVMLicenceAvailableVersion    OBJECT-TYPE
    SYNTAX    DisplayString (SIZE(0..40))
    MAX-ACCESS    read-only
    STATUS    current
    DESCRIPTION    "This shows the HVM licence information of partition1 (available version)."
    ::= { partition1BasicInfo 7 }

partition1BladeConfig    OBJECT IDENTIFIER ::= { partition1BasicInfo 20 } 

partition1BladePrimarySlotNum    OBJECT-TYPE
    SYNTAX    Integer32
    MAX-ACCESS    read-only
    STATUS    current
    DESCRIPTION    "This shows the primary blade location of partition1."
    ::= { partition1BladeConfig 1 }

partition1BladeCount    OBJECT-TYPE
    SYNTAX    Integer32
    MAX-ACCESS    read-only
    STATUS    current
    DESCRIPTION    "This shows the number of blades that belong to the partition1."
    ::= { partition1BladeConfig 2 }

partition1BladeTable    OBJECT-TYPE
    SYNTAX SEQUENCE OF partition1BladeEntry
    MAX-ACCESS not-accessible
    STATUS     current
    DESCRIPTION "This shows the table of blade information of partition1."
    ::= { partition1BladeConfig 3 }

partition1BladeEntry    OBJECT-TYPE
    SYNTAX Partition1BladeEntry
    MAX-ACCESS not-accessible
    STATUS    current
    DESCRIPTION "This shows the entry of blade information of partition1."
    INDEX { partition1BladeIndex }
    ::= { partition1BladeTable 1 }

partition1BladeIndex    OBJECT-TYPE
    SYNTAX    Integer32
    MAX-ACCESS    read-only
    STATUS    current
    DESCRIPTION    "This shows the index of blade information of partition1."
    ::= { partition1BladeEntry 1 }

partition1BladeSlotNum    OBJECT-TYPE
    SYNTAX    Integer32
    MAX-ACCESS    read-only
    STATUS    current
    DESCRIPTION    "This shows the location of blade of partition1."
    ::= { partition1BladeEntry 2 }

partition1BladeObjectID    OBJECT-TYPE
    SYNTAX    OBJECT IDENTIFIER
    MAX-ACCESS    read-only
    STATUS    current
    DESCRIPTION    "This shows the Object ID of blade of partition1."
    ::= { partition1BladeEntry 3 }

Partition1BladeEntry ::= SEQUENCE {
    partition1BladeIndex
        Integer32,
    partition1BladeSlotNum
        Integer32,
    partition1BladeObjectID
        OBJECT IDENTIFIER
}

partition1Settings    OBJECT IDENTIFIER ::= { partition1 3 } 

partition1SettingsSystemMode    OBJECT-TYPE
    SYNTAX    INTEGER {
    basic(1), hvm(2), unknown(3)
    }
    MAX-ACCESS    read-only
    STATUS    current
    DESCRIPTION    "This shows the hvm mode setting of partition1."
    ::= { partition1Settings 1 }

partition1SettingsDIMMRedundancy    OBJECT-TYPE
    SYNTAX    INTEGER {
    redundancy(1), non-redundancy(2),unknown(3)
    }
    MAX-ACCESS    read-only
    STATUS    current
    DESCRIPTION    "This shows the DIMM redundancy of partition1."
    ::= { partition1Settings 2 }

partition1SettingsPreConfig    OBJECT-TYPE
    SYNTAX    INTEGER {
    enable(1), disable(2), unknown(3)
    }
    MAX-ACCESS    read-only
    STATUS    current
    DESCRIPTION    "This shows the validity of pre-configure setting of partition1."
    ::= { partition1Settings 3 }

partition1State    OBJECT IDENTIFIER ::= { partition1 4 } 

partition1StatePower    OBJECT-TYPE
    SYNTAX    INTEGER {
    poweroff (1), standby (2), poweron (3), unknown (4),poweron-executing (5),poweroff-executing (6)
    }
    MAX-ACCESS    read-only
    STATUS    current
    DESCRIPTION    "This shows the power supply state of partition1."
    ::= { partition1State 1 }

partition1StateHealth    OBJECT-TYPE
    SYNTAX    INTEGER {
    normal (1),fail (2),unknown (3)
    }
    MAX-ACCESS    read-only
    STATUS    current
    DESCRIPTION    "This shows the health state of partition1."
    ::= { partition1State 2 }

partition1StateSystemMode    OBJECT-TYPE
    SYNTAX    INTEGER {
    basic(1), hvm(2), unknown(3)
    }
    MAX-ACCESS    read-only
    STATUS    current
    DESCRIPTION    "This shows the hvm mode of partition1."
    ::= { partition1State 3 }

partition1StateConsumptionCurrent    OBJECT-TYPE
    SYNTAX    Integer32
    UNITS    "0.1 A"
    MAX-ACCESS    read-only
    STATUS    current
    DESCRIPTION    "This shows the consumption current of partition1."
    ::= { partition1State 4 }

partition1StatePowerConsumption    OBJECT-TYPE
    SYNTAX    Integer32
    UNITS    "W"
    MAX-ACCESS    read-only
    STATUS    current
    DESCRIPTION    "This shows the current power consumption of partition1."
    ::= { partition1State 5 }

partition1StatePreConfig    OBJECT-TYPE
    SYNTAX    INTEGER {
    not-get(1), not-set(2), getting(3), valid(4)
    }
    MAX-ACCESS    read-only
    STATUS    current
    DESCRIPTION    "This shows the run state of pre-configure of partition1."
    ::= { partition1State 6 }

partition2    OBJECT IDENTIFIER ::= { partition 2 } 

partition2BasicInfo    OBJECT IDENTIFIER ::= { partition2 1 } 

partition2Valid    OBJECT-TYPE
    SYNTAX    INTEGER {
    invalid(1), valid(2) ,unknown(3)
    }
    MAX-ACCESS    read-only
    STATUS    current
    DESCRIPTION    "This shows the validity of information of partition2."
    ::= { partition2BasicInfo 1 }

partition2MaxCurrent    OBJECT-TYPE
    SYNTAX    Integer32
    UNITS    "0.1 A"
    MAX-ACCESS    read-only
    STATUS    current
    DESCRIPTION    "This shows the maximum current of partition2."
    ::= { partition2BasicInfo 2 }

partition2MaxPower    OBJECT-TYPE
    SYNTAX    Integer32
    UNITS    "W"
    MAX-ACCESS    read-only
    STATUS    current
    DESCRIPTION    "This shows the maximum power of partition2."
    ::= { partition2BasicInfo 3 }

partition2ProcCoreCount    OBJECT-TYPE
    SYNTAX    Integer32
    MAX-ACCESS    read-only
    STATUS    current
    DESCRIPTION    "This shows the total number of CPU core of partition2."
    ::= { partition2BasicInfo 4 }

partition2DIMMCapacity    OBJECT-TYPE
    SYNTAX    Integer32
    UNITS    "GB"
    MAX-ACCESS    read-only
    STATUS    current
    DESCRIPTION    "This shows the total amount of DIMM capacity of partition2."
    ::= { partition2BasicInfo 5 }

partition2HVMLicenceModel    OBJECT-TYPE
    SYNTAX    DisplayString (SIZE(0..40))
    MAX-ACCESS    read-only
    STATUS    current
    DESCRIPTION    "This shows the HVM licence information of partition2 (model)."
    ::= { partition2BasicInfo 6 }

partition2HVMLicenceAvailableVersion    OBJECT-TYPE
    SYNTAX    DisplayString (SIZE(0..40))
    MAX-ACCESS    read-only
    STATUS    current
    DESCRIPTION    "This shows the HVM licence information of partition2 (available version)."
    ::= { partition2BasicInfo 7 }

partition2BladeConfig    OBJECT IDENTIFIER ::= { partition2BasicInfo 20 } 

partition2BladePrimarySlotNum    OBJECT-TYPE
    SYNTAX    Integer32
    MAX-ACCESS    read-only
    STATUS    current
    DESCRIPTION    "This shows the primary blade location of partition2."
    ::= { partition2BladeConfig 1 }

partition2BladeCount    OBJECT-TYPE
    SYNTAX    Integer32
    MAX-ACCESS    read-only
    STATUS    current
    DESCRIPTION    "This shows the number of blades that belong to the partition2."
    ::= { partition2BladeConfig 2 }

partition2BladeTable    OBJECT-TYPE
    SYNTAX SEQUENCE OF partition2BladeEntry
    MAX-ACCESS not-accessible
    STATUS     current
    DESCRIPTION "This shows the table of blade information of partition2."
    ::= { partition2BladeConfig 3 }

partition2BladeEntry    OBJECT-TYPE
    SYNTAX Partition2BladeEntry
    MAX-ACCESS not-accessible
    STATUS    current
    DESCRIPTION "This shows the entry of blade information of partition2."
    INDEX { partition2BladeIndex }
    ::= { partition2BladeTable 1 }

partition2BladeIndex    OBJECT-TYPE
    SYNTAX    Integer32
    MAX-ACCESS    read-only
    STATUS    current
    DESCRIPTION    "This shows the index of blade information of partition2."
    ::= { partition2BladeEntry 1 }

partition2BladeSlotNum    OBJECT-TYPE
    SYNTAX    Integer32
    MAX-ACCESS    read-only
    STATUS    current
    DESCRIPTION    "This shows the location of blade of partition2."
    ::= { partition2BladeEntry 2 }

partition2BladeObjectID    OBJECT-TYPE
    SYNTAX    OBJECT IDENTIFIER
    MAX-ACCESS    read-only
    STATUS    current
    DESCRIPTION    "This shows the Object ID of blade of partition2."
    ::= { partition2BladeEntry 3 }

Partition2BladeEntry ::= SEQUENCE {
    partition2BladeIndex
        Integer32,
    partition2BladeSlotNum
        Integer32,
    partition2BladeObjectID
        OBJECT IDENTIFIER
}

partition2Settings    OBJECT IDENTIFIER ::= { partition2 3 } 

partition2SettingsSystemMode    OBJECT-TYPE
    SYNTAX    INTEGER {
    basic(1), hvm(2), unknown(3)
    }
    MAX-ACCESS    read-only
    STATUS    current
    DESCRIPTION    "This shows the hvm mode setting of partition2."
    ::= { partition2Settings 1 }

partition2SettingsDIMMRedundancy    OBJECT-TYPE
    SYNTAX    INTEGER {
    redundancy(1), non-redundancy(2),unknown(3)
    }
    MAX-ACCESS    read-only
    STATUS    current
    DESCRIPTION    "This shows the DIMM redundancy of partition2."
    ::= { partition2Settings 2 }

partition2SettingsPreConfig    OBJECT-TYPE
    SYNTAX    INTEGER {
    enable(1), disable(2), unknown(3)
    }
    MAX-ACCESS    read-only
    STATUS    current
    DESCRIPTION    "This shows the validity of pre-configure setting of partition2."
    ::= { partition2Settings 3 }

partition2State    OBJECT IDENTIFIER ::= { partition2 4 } 

partition2StatePower    OBJECT-TYPE
    SYNTAX    INTEGER {
    poweroff (1), standby (2), poweron (3), unknown (4),poweron-executing (5),poweroff-executing (6)
    }
    MAX-ACCESS    read-only
    STATUS    current
    DESCRIPTION    "This shows the power supply state of partition2."
    ::= { partition2State 1 }

partition2StateHealth    OBJECT-TYPE
    SYNTAX    INTEGER {
    normal (1),fail (2),unknown (3)
    }
    MAX-ACCESS    read-only
    STATUS    current
    DESCRIPTION    "This shows the health state of partition2."
    ::= { partition2State 2 }

partition2StateSystemMode    OBJECT-TYPE
    SYNTAX    INTEGER {
    basic(1), hvm(2), unknown(3)
    }
    MAX-ACCESS    read-only
    STATUS    current
    DESCRIPTION    "This shows the hvm mode of partition2."
    ::= { partition2State 3 }

partition2StateConsumptionCurrent    OBJECT-TYPE
    SYNTAX    Integer32
    UNITS    "0.1 A"
    MAX-ACCESS    read-only
    STATUS    current
    DESCRIPTION    "This shows the consumption current of partition2."
    ::= { partition2State 4 }

partition2StatePowerConsumption    OBJECT-TYPE
    SYNTAX    Integer32
    UNITS    "W"
    MAX-ACCESS    read-only
    STATUS    current
    DESCRIPTION    "This shows the current power consumption of partition2."
    ::= { partition2State 5 }

partition2StatePreConfig    OBJECT-TYPE
    SYNTAX    INTEGER {
    not-get(1), not-set(2), getting(3), valid(4)
    }
    MAX-ACCESS    read-only
    STATUS    current
    DESCRIPTION    "This shows the run state of pre-configure of partition2."
    ::= { partition2State 6 }

partition3    OBJECT IDENTIFIER ::= { partition 3 } 

partition3BasicInfo    OBJECT IDENTIFIER ::= { partition3 1 } 

partition3Valid    OBJECT-TYPE
    SYNTAX    INTEGER {
    invalid(1), valid(2) ,unknown(3)
    }
    MAX-ACCESS    read-only
    STATUS    current
    DESCRIPTION    "This shows the validity of information of partition3."
    ::= { partition3BasicInfo 1 }

partition3MaxCurrent    OBJECT-TYPE
    SYNTAX    Integer32
    UNITS    "0.1 A"
    MAX-ACCESS    read-only
    STATUS    current
    DESCRIPTION    "This shows the maximum current of partition3."
    ::= { partition3BasicInfo 2 }

partition3MaxPower    OBJECT-TYPE
    SYNTAX    Integer32
    UNITS    "W"
    MAX-ACCESS    read-only
    STATUS    current
    DESCRIPTION    "This shows the maximum power of partition3."
    ::= { partition3BasicInfo 3 }

partition3ProcCoreCount    OBJECT-TYPE
    SYNTAX    Integer32
    MAX-ACCESS    read-only
    STATUS    current
    DESCRIPTION    "This shows the total number of CPU core of partition3."
    ::= { partition3BasicInfo 4 }

partition3DIMMCapacity    OBJECT-TYPE
    SYNTAX    Integer32
    UNITS    "GB"
    MAX-ACCESS    read-only
    STATUS    current
    DESCRIPTION    "This shows the total amount of DIMM capacity of partition3."
    ::= { partition3BasicInfo 5 }

partition3HVMLicenceModel    OBJECT-TYPE
    SYNTAX    DisplayString (SIZE(0..40))
    MAX-ACCESS    read-only
    STATUS    current
    DESCRIPTION    "This shows the HVM licence information of partition3 (model)."
    ::= { partition3BasicInfo 6 }

partition3HVMLicenceAvailableVersion    OBJECT-TYPE
    SYNTAX    DisplayString (SIZE(0..40))
    MAX-ACCESS    read-only
    STATUS    current
    DESCRIPTION    "This shows the HVM licence information of partition3 (available version)."
    ::= { partition3BasicInfo 7 }

partition3BladeConfig    OBJECT IDENTIFIER ::= { partition3BasicInfo 20 } 

partition3BladePrimarySlotNum    OBJECT-TYPE
    SYNTAX    Integer32
    MAX-ACCESS    read-only
    STATUS    current
    DESCRIPTION    "This shows the primary blade location of partition3."
    ::= { partition3BladeConfig 1 }

partition3BladeCount    OBJECT-TYPE
    SYNTAX    Integer32
    MAX-ACCESS    read-only
    STATUS    current
    DESCRIPTION    "This shows the number of blades that belong to the partition3."
    ::= { partition3BladeConfig 2 }

partition3BladeTable    OBJECT-TYPE
    SYNTAX SEQUENCE OF partition3BladeEntry
    MAX-ACCESS not-accessible
    STATUS     current
    DESCRIPTION "This shows the table of blade information of partition3."
    ::= { partition3BladeConfig 3 }

partition3BladeEntry    OBJECT-TYPE
    SYNTAX Partition3BladeEntry
    MAX-ACCESS not-accessible
    STATUS    current
    DESCRIPTION "This shows the entry of blade information of partition3."
    INDEX { partition3BladeIndex }
    ::= { partition3BladeTable 1 }

partition3BladeIndex    OBJECT-TYPE
    SYNTAX    Integer32
    MAX-ACCESS    read-only
    STATUS    current
    DESCRIPTION    "This shows the index of blade information of partition3."
    ::= { partition3BladeEntry 1 }

partition3BladeSlotNum    OBJECT-TYPE
    SYNTAX    Integer32
    MAX-ACCESS    read-only
    STATUS    current
    DESCRIPTION    "This shows the location of blade of partition3."
    ::= { partition3BladeEntry 2 }

partition3BladeObjectID    OBJECT-TYPE
    SYNTAX    OBJECT IDENTIFIER
    MAX-ACCESS    read-only
    STATUS    current
    DESCRIPTION    "This shows the Object ID of blade of partition3."
    ::= { partition3BladeEntry 3 }

Partition3BladeEntry ::= SEQUENCE {
    partition3BladeIndex
        Integer32,
    partition3BladeSlotNum
        Integer32,
    partition3BladeObjectID
        OBJECT IDENTIFIER
}

partition3Settings    OBJECT IDENTIFIER ::= { partition3 3 } 

partition3SettingsSystemMode    OBJECT-TYPE
    SYNTAX    INTEGER {
    basic(1), hvm(2), unknown(3)
    }
    MAX-ACCESS    read-only
    STATUS    current
    DESCRIPTION    "This shows the hvm mode setting of partition3."
    ::= { partition3Settings 1 }

partition3SettingsDIMMRedundancy    OBJECT-TYPE
    SYNTAX    INTEGER {
    redundancy(1), non-redundancy(2),unknown(3)
    }
    MAX-ACCESS    read-only
    STATUS    current
    DESCRIPTION    "This shows the DIMM redundancy of partition3."
    ::= { partition3Settings 2 }

partition3SettingsPreConfig    OBJECT-TYPE
    SYNTAX    INTEGER {
    enable(1), disable(2), unknown(3)
    }
    MAX-ACCESS    read-only
    STATUS    current
    DESCRIPTION    "This shows the validity of pre-configure setting of partition3."
    ::= { partition3Settings 3 }

partition3State    OBJECT IDENTIFIER ::= { partition3 4 } 

partition3StatePower    OBJECT-TYPE
    SYNTAX    INTEGER {
    poweroff (1), standby (2), poweron (3), unknown (4),poweron-executing (5),poweroff-executing (6)
    }
    MAX-ACCESS    read-only
    STATUS    current
    DESCRIPTION    "This shows the power supply state of partition3."
    ::= { partition3State 1 }

partition3StateHealth    OBJECT-TYPE
    SYNTAX    INTEGER {
    normal (1),fail (2),unknown (3)
    }
    MAX-ACCESS    read-only
    STATUS    current
    DESCRIPTION    "This shows the health state of partition3."
    ::= { partition3State 2 }

partition3StateSystemMode    OBJECT-TYPE
    SYNTAX    INTEGER {
    basic(1), hvm(2), unknown(3)
    }
    MAX-ACCESS    read-only
    STATUS    current
    DESCRIPTION    "This shows the hvm mode of partition3."
    ::= { partition3State 3 }

partition3StateConsumptionCurrent    OBJECT-TYPE
    SYNTAX    Integer32
    UNITS    "0.1 A"
    MAX-ACCESS    read-only
    STATUS    current
    DESCRIPTION    "This shows the consumption current of partition3."
    ::= { partition3State 4 }

partition3StatePowerConsumption    OBJECT-TYPE
    SYNTAX    Integer32
    UNITS    "W"
    MAX-ACCESS    read-only
    STATUS    current
    DESCRIPTION    "This shows the current power consumption of partition3."
    ::= { partition3State 5 }

partition3StatePreConfig    OBJECT-TYPE
    SYNTAX    INTEGER {
    not-get(1), not-set(2), getting(3), valid(4)
    }
    MAX-ACCESS    read-only
    STATUS    current
    DESCRIPTION    "This shows the run state of pre-configure of partition3."
    ::= { partition3State 6 }

partition4    OBJECT IDENTIFIER ::= { partition 4 } 

partition4BasicInfo    OBJECT IDENTIFIER ::= { partition4 1 } 

partition4Valid    OBJECT-TYPE
    SYNTAX    INTEGER {
    invalid(1), valid(2) ,unknown(3)
    }
    MAX-ACCESS    read-only
    STATUS    current
    DESCRIPTION    "This shows the validity of information of partition4."
    ::= { partition4BasicInfo 1 }

partition4MaxCurrent    OBJECT-TYPE
    SYNTAX    Integer32
    UNITS    "0.1 A"
    MAX-ACCESS    read-only
    STATUS    current
    DESCRIPTION    "This shows the maximum current of partition4."
    ::= { partition4BasicInfo 2 }

partition4MaxPower    OBJECT-TYPE
    SYNTAX    Integer32
    UNITS    "W"
    MAX-ACCESS    read-only
    STATUS    current
    DESCRIPTION    "This shows the maximum power of partition4."
    ::= { partition4BasicInfo 3 }

partition4ProcCoreCount    OBJECT-TYPE
    SYNTAX    Integer32
    MAX-ACCESS    read-only
    STATUS    current
    DESCRIPTION    "This shows the total number of CPU core of partition4."
    ::= { partition4BasicInfo 4 }

partition4DIMMCapacity    OBJECT-TYPE
    SYNTAX    Integer32
    UNITS    "GB"
    MAX-ACCESS    read-only
    STATUS    current
    DESCRIPTION    "This shows the total amount of DIMM capacity of partition4."
    ::= { partition4BasicInfo 5 }

partition4HVMLicenceModel    OBJECT-TYPE
    SYNTAX    DisplayString (SIZE(0..40))
    MAX-ACCESS    read-only
    STATUS    current
    DESCRIPTION    "This shows the HVM licence information of partition4 (model)."
    ::= { partition4BasicInfo 6 }

partition4HVMLicenceAvailableVersion    OBJECT-TYPE
    SYNTAX    DisplayString (SIZE(0..40))
    MAX-ACCESS    read-only
    STATUS    current
    DESCRIPTION    "This shows the HVM licence information of partition4 (available version)."
    ::= { partition4BasicInfo 7 }

partition4BladeConfig    OBJECT IDENTIFIER ::= { partition4BasicInfo 20 } 

partition4BladePrimarySlotNum    OBJECT-TYPE
    SYNTAX    Integer32
    MAX-ACCESS    read-only
    STATUS    current
    DESCRIPTION    "This shows the primary blade location of partition4."
    ::= { partition4BladeConfig 1 }

partition4BladeCount    OBJECT-TYPE
    SYNTAX    Integer32
    MAX-ACCESS    read-only
    STATUS    current
    DESCRIPTION    "This shows the number of blades that belong to the partition4."
    ::= { partition4BladeConfig 2 }

partition4BladeTable    OBJECT-TYPE
    SYNTAX SEQUENCE OF partition4BladeEntry
    MAX-ACCESS not-accessible
    STATUS     current
    DESCRIPTION "This shows the table of blade information of partition4."
    ::= { partition4BladeConfig 3 }

partition4BladeEntry    OBJECT-TYPE
    SYNTAX Partition4BladeEntry
    MAX-ACCESS not-accessible
    STATUS    current
    DESCRIPTION "This shows the entry of blade information of partition4."
    INDEX { partition4BladeIndex }
    ::= { partition4BladeTable 1 }

partition4BladeIndex    OBJECT-TYPE
    SYNTAX    Integer32
    MAX-ACCESS    read-only
    STATUS    current
    DESCRIPTION    "This shows the index of blade information of partition4."
    ::= { partition4BladeEntry 1 }

partition4BladeSlotNum    OBJECT-TYPE
    SYNTAX    Integer32
    MAX-ACCESS    read-only
    STATUS    current
    DESCRIPTION    "This shows the location of blade of partition4."
    ::= { partition4BladeEntry 2 }

partition4BladeObjectID    OBJECT-TYPE
    SYNTAX    OBJECT IDENTIFIER
    MAX-ACCESS    read-only
    STATUS    current
    DESCRIPTION    "This shows the Object ID of blade of partition4."
    ::= { partition4BladeEntry 3 }

Partition4BladeEntry ::= SEQUENCE {
    partition4BladeIndex
        Integer32,
    partition4BladeSlotNum
        Integer32,
    partition4BladeObjectID
        OBJECT IDENTIFIER
}

partition4Settings    OBJECT IDENTIFIER ::= { partition4 3 } 

partition4SettingsSystemMode    OBJECT-TYPE
    SYNTAX    INTEGER {
    basic(1), hvm(2), unknown(3)
    }
    MAX-ACCESS    read-only
    STATUS    current
    DESCRIPTION    "This shows the hvm mode setting of partition4."
    ::= { partition4Settings 1 }

partition4SettingsDIMMRedundancy    OBJECT-TYPE
    SYNTAX    INTEGER {
    redundancy(1), non-redundancy(2),unknown(3)
    }
    MAX-ACCESS    read-only
    STATUS    current
    DESCRIPTION    "This shows the DIMM redundancy of partition4."
    ::= { partition4Settings 2 }

partition4SettingsPreConfig    OBJECT-TYPE
    SYNTAX    INTEGER {
    enable(1), disable(2), unknown(3)
    }
    MAX-ACCESS    read-only
    STATUS    current
    DESCRIPTION    "This shows the validity of pre-configure setting of partition4."
    ::= { partition4Settings 3 }

partition4State    OBJECT IDENTIFIER ::= { partition4 4 } 

partition4StatePower    OBJECT-TYPE
    SYNTAX    INTEGER {
    poweroff (1), standby (2), poweron (3), unknown (4),poweron-executing (5),poweroff-executing (6)
    }
    MAX-ACCESS    read-only
    STATUS    current
    DESCRIPTION    "This shows the power supply state of partition4."
    ::= { partition4State 1 }

partition4StateHealth    OBJECT-TYPE
    SYNTAX    INTEGER {
    normal (1),fail (2),unknown (3)
    }
    MAX-ACCESS    read-only
    STATUS    current
    DESCRIPTION    "This shows the health state of partition4."
    ::= { partition4State 2 }

partition4StateSystemMode    OBJECT-TYPE
    SYNTAX    INTEGER {
    basic(1), hvm(2), unknown(3)
    }
    MAX-ACCESS    read-only
    STATUS    current
    DESCRIPTION    "This shows the hvm mode of partition4."
    ::= { partition4State 3 }

partition4StateConsumptionCurrent    OBJECT-TYPE
    SYNTAX    Integer32
    UNITS    "0.1 A"
    MAX-ACCESS    read-only
    STATUS    current
    DESCRIPTION    "This shows the consumption current of partition4."
    ::= { partition4State 4 }

partition4StatePowerConsumption    OBJECT-TYPE
    SYNTAX    Integer32
    UNITS    "W"
    MAX-ACCESS    read-only
    STATUS    current
    DESCRIPTION    "This shows the current power consumption of partition4."
    ::= { partition4State 5 }

partition4StatePreConfig    OBJECT-TYPE
    SYNTAX    INTEGER {
    not-get(1), not-set(2), getting(3), valid(4)
    }
    MAX-ACCESS    read-only
    STATUS    current
    DESCRIPTION    "This shows the run state of pre-configure of partition4."
    ::= { partition4State 6 }

partition5    OBJECT IDENTIFIER ::= { partition 5 } 

partition5BasicInfo    OBJECT IDENTIFIER ::= { partition5 1 } 

partition5Valid    OBJECT-TYPE
    SYNTAX    INTEGER {
    invalid(1), valid(2) ,unknown(3)
    }
    MAX-ACCESS    read-only
    STATUS    current
    DESCRIPTION    "This shows the validity of information of partition5."
    ::= { partition5BasicInfo 1 }

partition5MaxCurrent    OBJECT-TYPE
    SYNTAX    Integer32
    UNITS    "0.1 A"
    MAX-ACCESS    read-only
    STATUS    current
    DESCRIPTION    "This shows the maximum current of partition5."
    ::= { partition5BasicInfo 2 }

partition5MaxPower    OBJECT-TYPE
    SYNTAX    Integer32
    UNITS    "W"
    MAX-ACCESS    read-only
    STATUS    current
    DESCRIPTION    "This shows the maximum power of partition5."
    ::= { partition5BasicInfo 3 }

partition5ProcCoreCount    OBJECT-TYPE
    SYNTAX    Integer32
    MAX-ACCESS    read-only
    STATUS    current
    DESCRIPTION    "This shows the total number of CPU core of partition5."
    ::= { partition5BasicInfo 4 }

partition5DIMMCapacity    OBJECT-TYPE
    SYNTAX    Integer32
    UNITS    "GB"
    MAX-ACCESS    read-only
    STATUS    current
    DESCRIPTION    "This shows the total amount of DIMM capacity of partition5."
    ::= { partition5BasicInfo 5 }

partition5HVMLicenceModel    OBJECT-TYPE
    SYNTAX    DisplayString (SIZE(0..40))
    MAX-ACCESS    read-only
    STATUS    current
    DESCRIPTION    "This shows the HVM licence information of partition5 (model)."
    ::= { partition5BasicInfo 6 }

partition5HVMLicenceAvailableVersion    OBJECT-TYPE
    SYNTAX    DisplayString (SIZE(0..40))
    MAX-ACCESS    read-only
    STATUS    current
    DESCRIPTION    "This shows the HVM licence information of partition5 (available version)."
    ::= { partition5BasicInfo 7 }

partition5BladeConfig    OBJECT IDENTIFIER ::= { partition5BasicInfo 20 } 

partition5BladePrimarySlotNum    OBJECT-TYPE
    SYNTAX    Integer32
    MAX-ACCESS    read-only
    STATUS    current
    DESCRIPTION    "This shows the primary blade location of partition5."
    ::= { partition5BladeConfig 1 }

partition5BladeCount    OBJECT-TYPE
    SYNTAX    Integer32
    MAX-ACCESS    read-only
    STATUS    current
    DESCRIPTION    "This shows the number of blades that belong to the partition5."
    ::= { partition5BladeConfig 2 }

partition5BladeTable    OBJECT-TYPE
    SYNTAX SEQUENCE OF partition5BladeEntry
    MAX-ACCESS not-accessible
    STATUS     current
    DESCRIPTION "This shows the table of blade information of partition5."
    ::= { partition5BladeConfig 3 }

partition5BladeEntry    OBJECT-TYPE
    SYNTAX Partition5BladeEntry
    MAX-ACCESS not-accessible
    STATUS    current
    DESCRIPTION "This shows the entry of blade information of partition5."
    INDEX { partition5BladeIndex }
    ::= { partition5BladeTable 1 }

partition5BladeIndex    OBJECT-TYPE
    SYNTAX    Integer32
    MAX-ACCESS    read-only
    STATUS    current
    DESCRIPTION    "This shows the index of blade information of partition5."
    ::= { partition5BladeEntry 1 }

partition5BladeSlotNum    OBJECT-TYPE
    SYNTAX    Integer32
    MAX-ACCESS    read-only
    STATUS    current
    DESCRIPTION    "This shows the location of blade of partition5."
    ::= { partition5BladeEntry 2 }

partition5BladeObjectID    OBJECT-TYPE
    SYNTAX    OBJECT IDENTIFIER
    MAX-ACCESS    read-only
    STATUS    current
    DESCRIPTION    "This shows the Object ID of blade of partition5."
    ::= { partition5BladeEntry 3 }

Partition5BladeEntry ::= SEQUENCE {
    partition5BladeIndex
        Integer32,
    partition5BladeSlotNum
        Integer32,
    partition5BladeObjectID
        OBJECT IDENTIFIER
}

partition5Settings    OBJECT IDENTIFIER ::= { partition5 3 } 

partition5SettingsSystemMode    OBJECT-TYPE
    SYNTAX    INTEGER {
    basic(1), hvm(2), unknown(3)
    }
    MAX-ACCESS    read-only
    STATUS    current
    DESCRIPTION    "This shows the hvm mode setting of partition5."
    ::= { partition5Settings 1 }

partition5SettingsDIMMRedundancy    OBJECT-TYPE
    SYNTAX    INTEGER {
    redundancy(1), non-redundancy(2),unknown(3)
    }
    MAX-ACCESS    read-only
    STATUS    current
    DESCRIPTION    "This shows the DIMM redundancy of partition5."
    ::= { partition5Settings 2 }

partition5SettingsPreConfig    OBJECT-TYPE
    SYNTAX    INTEGER {
    enable(1), disable(2), unknown(3)
    }
    MAX-ACCESS    read-only
    STATUS    current
    DESCRIPTION    "This shows the validity of pre-configure setting of partition5."
    ::= { partition5Settings 3 }

partition5State    OBJECT IDENTIFIER ::= { partition5 4 } 

partition5StatePower    OBJECT-TYPE
    SYNTAX    INTEGER {
    poweroff (1), standby (2), poweron (3), unknown (4),poweron-executing (5),poweroff-executing (6)
    }
    MAX-ACCESS    read-only
    STATUS    current
    DESCRIPTION    "This shows the power supply state of partition5."
    ::= { partition5State 1 }

partition5StateHealth    OBJECT-TYPE
    SYNTAX    INTEGER {
    normal (1),fail (2),unknown (3)
    }
    MAX-ACCESS    read-only
    STATUS    current
    DESCRIPTION    "This shows the health state of partition5."
    ::= { partition5State 2 }

partition5StateSystemMode    OBJECT-TYPE
    SYNTAX    INTEGER {
    basic(1), hvm(2), unknown(3)
    }
    MAX-ACCESS    read-only
    STATUS    current
    DESCRIPTION    "This shows the hvm mode of partition5."
    ::= { partition5State 3 }

partition5StateConsumptionCurrent    OBJECT-TYPE
    SYNTAX    Integer32
    UNITS    "0.1 A"
    MAX-ACCESS    read-only
    STATUS    current
    DESCRIPTION    "This shows the consumption current of partition5."
    ::= { partition5State 4 }

partition5StatePowerConsumption    OBJECT-TYPE
    SYNTAX    Integer32
    UNITS    "W"
    MAX-ACCESS    read-only
    STATUS    current
    DESCRIPTION    "This shows the current power consumption of partition5."
    ::= { partition5State 5 }

partition5StatePreConfig    OBJECT-TYPE
    SYNTAX    INTEGER {
    not-get(1), not-set(2), getting(3), valid(4)
    }
    MAX-ACCESS    read-only
    STATUS    current
    DESCRIPTION    "This shows the run state of pre-configure of partition5."
    ::= { partition5State 6 }

partition6    OBJECT IDENTIFIER ::= { partition 6 } 

partition6BasicInfo    OBJECT IDENTIFIER ::= { partition6 1 } 

partition6Valid    OBJECT-TYPE
    SYNTAX    INTEGER {
    invalid(1), valid(2) ,unknown(3)
    }
    MAX-ACCESS    read-only
    STATUS    current
    DESCRIPTION    "This shows the validity of information of partition6."
    ::= { partition6BasicInfo 1 }

partition6MaxCurrent    OBJECT-TYPE
    SYNTAX    Integer32
    UNITS    "0.1 A"
    MAX-ACCESS    read-only
    STATUS    current
    DESCRIPTION    "This shows the maximum current of partition6."
    ::= { partition6BasicInfo 2 }

partition6MaxPower    OBJECT-TYPE
    SYNTAX    Integer32
    UNITS    "W"
    MAX-ACCESS    read-only
    STATUS    current
    DESCRIPTION    "This shows the maximum power of partition6."
    ::= { partition6BasicInfo 3 }

partition6ProcCoreCount    OBJECT-TYPE
    SYNTAX    Integer32
    MAX-ACCESS    read-only
    STATUS    current
    DESCRIPTION    "This shows the total number of CPU core of partition6."
    ::= { partition6BasicInfo 4 }

partition6DIMMCapacity    OBJECT-TYPE
    SYNTAX    Integer32
    UNITS    "GB"
    MAX-ACCESS    read-only
    STATUS    current
    DESCRIPTION    "This shows the total amount of DIMM capacity of partition6."
    ::= { partition6BasicInfo 5 }

partition6HVMLicenceModel    OBJECT-TYPE
    SYNTAX    DisplayString (SIZE(0..40))
    MAX-ACCESS    read-only
    STATUS    current
    DESCRIPTION    "This shows the HVM licence information of partition6 (model)."
    ::= { partition6BasicInfo 6 }

partition6HVMLicenceAvailableVersion    OBJECT-TYPE
    SYNTAX    DisplayString (SIZE(0..40))
    MAX-ACCESS    read-only
    STATUS    current
    DESCRIPTION    "This shows the HVM licence information of partition6 (available version)."
    ::= { partition6BasicInfo 7 }

partition6BladeConfig    OBJECT IDENTIFIER ::= { partition6BasicInfo 20 } 

partition6BladePrimarySlotNum    OBJECT-TYPE
    SYNTAX    Integer32
    MAX-ACCESS    read-only
    STATUS    current
    DESCRIPTION    "This shows the primary blade location of partition6."
    ::= { partition6BladeConfig 1 }

partition6BladeCount    OBJECT-TYPE
    SYNTAX    Integer32
    MAX-ACCESS    read-only
    STATUS    current
    DESCRIPTION    "This shows the number of blades that belong to the partition6."
    ::= { partition6BladeConfig 2 }

partition6BladeTable    OBJECT-TYPE
    SYNTAX SEQUENCE OF partition6BladeEntry
    MAX-ACCESS not-accessible
    STATUS     current
    DESCRIPTION "This shows the table of blade information of partition6."
    ::= { partition6BladeConfig 3 }

partition6BladeEntry    OBJECT-TYPE
    SYNTAX Partition6BladeEntry
    MAX-ACCESS not-accessible
    STATUS    current
    DESCRIPTION "This shows the entry of blade information of partition6."
    INDEX { partition6BladeIndex }
    ::= { partition6BladeTable 1 }

partition6BladeIndex    OBJECT-TYPE
    SYNTAX    Integer32
    MAX-ACCESS    read-only
    STATUS    current
    DESCRIPTION    "This shows the index of blade information of partition6."
    ::= { partition6BladeEntry 1 }

partition6BladeSlotNum    OBJECT-TYPE
    SYNTAX    Integer32
    MAX-ACCESS    read-only
    STATUS    current
    DESCRIPTION    "This shows the location of blade of partition6."
    ::= { partition6BladeEntry 2 }

partition6BladeObjectID    OBJECT-TYPE
    SYNTAX    OBJECT IDENTIFIER
    MAX-ACCESS    read-only
    STATUS    current
    DESCRIPTION    "This shows the Object ID of blade of partition6."
    ::= { partition6BladeEntry 3 }

Partition6BladeEntry ::= SEQUENCE {
    partition6BladeIndex
        Integer32,
    partition6BladeSlotNum
        Integer32,
    partition6BladeObjectID
        OBJECT IDENTIFIER
}

partition6Settings    OBJECT IDENTIFIER ::= { partition6 3 } 

partition6SettingsSystemMode    OBJECT-TYPE
    SYNTAX    INTEGER {
    basic(1), hvm(2), unknown(3)
    }
    MAX-ACCESS    read-only
    STATUS    current
    DESCRIPTION    "This shows the hvm mode setting of partition6."
    ::= { partition6Settings 1 }

partition6SettingsDIMMRedundancy    OBJECT-TYPE
    SYNTAX    INTEGER {
    redundancy(1), non-redundancy(2),unknown(3)
    }
    MAX-ACCESS    read-only
    STATUS    current
    DESCRIPTION    "This shows the DIMM redundancy of partition6."
    ::= { partition6Settings 2 }

partition6SettingsPreConfig    OBJECT-TYPE
    SYNTAX    INTEGER {
    enable(1), disable(2), unknown(3)
    }
    MAX-ACCESS    read-only
    STATUS    current
    DESCRIPTION    "This shows the validity of pre-configure setting of partition6."
    ::= { partition6Settings 3 }

partition6State    OBJECT IDENTIFIER ::= { partition6 4 } 

partition6StatePower    OBJECT-TYPE
    SYNTAX    INTEGER {
    poweroff (1), standby (2), poweron (3), unknown (4),poweron-executing (5),poweroff-executing (6)
    }
    MAX-ACCESS    read-only
    STATUS    current
    DESCRIPTION    "This shows the power supply state of partition6."
    ::= { partition6State 1 }

partition6StateHealth    OBJECT-TYPE
    SYNTAX    INTEGER {
    normal (1),fail (2),unknown (3)
    }
    MAX-ACCESS    read-only
    STATUS    current
    DESCRIPTION    "This shows the health state of partition6."
    ::= { partition6State 2 }

partition6StateSystemMode    OBJECT-TYPE
    SYNTAX    INTEGER {
    basic(1), hvm(2), unknown(3)
    }
    MAX-ACCESS    read-only
    STATUS    current
    DESCRIPTION    "This shows the hvm mode of partition6."
    ::= { partition6State 3 }

partition6StateConsumptionCurrent    OBJECT-TYPE
    SYNTAX    Integer32
    UNITS    "0.1 A"
    MAX-ACCESS    read-only
    STATUS    current
    DESCRIPTION    "This shows the consumption current of partition6."
    ::= { partition6State 4 }

partition6StatePowerConsumption    OBJECT-TYPE
    SYNTAX    Integer32
    UNITS    "W"
    MAX-ACCESS    read-only
    STATUS    current
    DESCRIPTION    "This shows the current power consumption of partition6."
    ::= { partition6State 5 }

partition6StatePreConfig    OBJECT-TYPE
    SYNTAX    INTEGER {
    not-get(1), not-set(2), getting(3), valid(4)
    }
    MAX-ACCESS    read-only
    STATUS    current
    DESCRIPTION    "This shows the run state of pre-configure of partition6."
    ::= { partition6State 6 }

partition7    OBJECT IDENTIFIER ::= { partition 7 } 

partition7BasicInfo    OBJECT IDENTIFIER ::= { partition7 1 } 

partition7Valid    OBJECT-TYPE
    SYNTAX    INTEGER {
    invalid(1), valid(2) ,unknown(3)
    }
    MAX-ACCESS    read-only
    STATUS    current
    DESCRIPTION    "This shows the validity of information of partition7."
    ::= { partition7BasicInfo 1 }

partition7MaxCurrent    OBJECT-TYPE
    SYNTAX    Integer32
    UNITS    "0.1 A"
    MAX-ACCESS    read-only
    STATUS    current
    DESCRIPTION    "This shows the maximum current of partition7."
    ::= { partition7BasicInfo 2 }

partition7MaxPower    OBJECT-TYPE
    SYNTAX    Integer32
    UNITS    "W"
    MAX-ACCESS    read-only
    STATUS    current
    DESCRIPTION    "This shows the maximum power of partition7."
    ::= { partition7BasicInfo 3 }

partition7ProcCoreCount    OBJECT-TYPE
    SYNTAX    Integer32
    MAX-ACCESS    read-only
    STATUS    current
    DESCRIPTION    "This shows the total number of CPU core of partition7."
    ::= { partition7BasicInfo 4 }

partition7DIMMCapacity    OBJECT-TYPE
    SYNTAX    Integer32
    UNITS    "GB"
    MAX-ACCESS    read-only
    STATUS    current
    DESCRIPTION    "This shows the total amount of DIMM capacity of partition7."
    ::= { partition7BasicInfo 5 }

partition7HVMLicenceModel    OBJECT-TYPE
    SYNTAX    DisplayString (SIZE(0..40))
    MAX-ACCESS    read-only
    STATUS    current
    DESCRIPTION    "This shows the HVM licence information of partition7 (model)."
    ::= { partition7BasicInfo 6 }

partition7HVMLicenceAvailableVersion    OBJECT-TYPE
    SYNTAX    DisplayString (SIZE(0..40))
    MAX-ACCESS    read-only
    STATUS    current
    DESCRIPTION    "This shows the HVM licence information of partition7 (available version)."
    ::= { partition7BasicInfo 7 }

partition7BladeConfig    OBJECT IDENTIFIER ::= { partition7BasicInfo 20 } 

partition7BladePrimarySlotNum    OBJECT-TYPE
    SYNTAX    Integer32
    MAX-ACCESS    read-only
    STATUS    current
    DESCRIPTION    "This shows the primary blade location of partition7."
    ::= { partition7BladeConfig 1 }

partition7BladeCount    OBJECT-TYPE
    SYNTAX    Integer32
    MAX-ACCESS    read-only
    STATUS    current
    DESCRIPTION    "This shows the number of blades that belong to the partition7."
    ::= { partition7BladeConfig 2 }

partition7BladeTable    OBJECT-TYPE
    SYNTAX SEQUENCE OF partition7BladeEntry
    MAX-ACCESS not-accessible
    STATUS     current
    DESCRIPTION "This shows the table of blade information of partition7."
    ::= { partition7BladeConfig 3 }

partition7BladeEntry    OBJECT-TYPE
    SYNTAX Partition7BladeEntry
    MAX-ACCESS not-accessible
    STATUS    current
    DESCRIPTION "This shows the entry of blade information of partition7."
    INDEX { partition7BladeIndex }
    ::= { partition7BladeTable 1 }

partition7BladeIndex    OBJECT-TYPE
    SYNTAX    Integer32
    MAX-ACCESS    read-only
    STATUS    current
    DESCRIPTION    "This shows the index of blade information of partition7."
    ::= { partition7BladeEntry 1 }

partition7BladeSlotNum    OBJECT-TYPE
    SYNTAX    Integer32
    MAX-ACCESS    read-only
    STATUS    current
    DESCRIPTION    "This shows the location of blade of partition7."
    ::= { partition7BladeEntry 2 }

partition7BladeObjectID    OBJECT-TYPE
    SYNTAX    OBJECT IDENTIFIER
    MAX-ACCESS    read-only
    STATUS    current
    DESCRIPTION    "This shows the Object ID of blade of partition7."
    ::= { partition7BladeEntry 3 }

Partition7BladeEntry ::= SEQUENCE {
    partition7BladeIndex
        Integer32,
    partition7BladeSlotNum
        Integer32,
    partition7BladeObjectID
        OBJECT IDENTIFIER
}

partition7Settings    OBJECT IDENTIFIER ::= { partition7 3 } 

partition7SettingsSystemMode    OBJECT-TYPE
    SYNTAX    INTEGER {
    basic(1), hvm(2), unknown(3)
    }
    MAX-ACCESS    read-only
    STATUS    current
    DESCRIPTION    "This shows the hvm mode setting of partition7."
    ::= { partition7Settings 1 }

partition7SettingsDIMMRedundancy    OBJECT-TYPE
    SYNTAX    INTEGER {
    redundancy(1), non-redundancy(2),unknown(3)
    }
    MAX-ACCESS    read-only
    STATUS    current
    DESCRIPTION    "This shows the DIMM redundancy of partition7."
    ::= { partition7Settings 2 }

partition7SettingsPreConfig    OBJECT-TYPE
    SYNTAX    INTEGER {
    enable(1), disable(2), unknown(3)
    }
    MAX-ACCESS    read-only
    STATUS    current
    DESCRIPTION    "This shows the validity of pre-configure setting of partition7."
    ::= { partition7Settings 3 }

partition7State    OBJECT IDENTIFIER ::= { partition7 4 } 

partition7StatePower    OBJECT-TYPE
    SYNTAX    INTEGER {
    poweroff (1), standby (2), poweron (3), unknown (4),poweron-executing (5),poweroff-executing (6)
    }
    MAX-ACCESS    read-only
    STATUS    current
    DESCRIPTION    "This shows the power supply state of partition7."
    ::= { partition7State 1 }

partition7StateHealth    OBJECT-TYPE
    SYNTAX    INTEGER {
    normal (1),fail (2),unknown (3)
    }
    MAX-ACCESS    read-only
    STATUS    current
    DESCRIPTION    "This shows the health state of partition7."
    ::= { partition7State 2 }

partition7StateSystemMode    OBJECT-TYPE
    SYNTAX    INTEGER {
    basic(1), hvm(2), unknown(3)
    }
    MAX-ACCESS    read-only
    STATUS    current
    DESCRIPTION    "This shows the hvm mode of partition7."
    ::= { partition7State 3 }

partition7StateConsumptionCurrent    OBJECT-TYPE
    SYNTAX    Integer32
    UNITS    "0.1 A"
    MAX-ACCESS    read-only
    STATUS    current
    DESCRIPTION    "This shows the consumption current of partition7."
    ::= { partition7State 4 }

partition7StatePowerConsumption    OBJECT-TYPE
    SYNTAX    Integer32
    UNITS    "W"
    MAX-ACCESS    read-only
    STATUS    current
    DESCRIPTION    "This shows the current power consumption of partition7."
    ::= { partition7State 5 }

partition7StatePreConfig    OBJECT-TYPE
    SYNTAX    INTEGER {
    not-get(1), not-set(2), getting(3), valid(4)
    }
    MAX-ACCESS    read-only
    STATUS    current
    DESCRIPTION    "This shows the run state of pre-configure of partition7."
    ::= { partition7State 6 }

partition8    OBJECT IDENTIFIER ::= { partition 8 } 

partition8BasicInfo    OBJECT IDENTIFIER ::= { partition8 1 } 

partition8Valid    OBJECT-TYPE
    SYNTAX    INTEGER {
    invalid(1), valid(2) ,unknown(3)
    }
    MAX-ACCESS    read-only
    STATUS    current
    DESCRIPTION    "This shows the validity of information of partition8."
    ::= { partition8BasicInfo 1 }

partition8MaxCurrent    OBJECT-TYPE
    SYNTAX    Integer32
    UNITS    "0.1 A"
    MAX-ACCESS    read-only
    STATUS    current
    DESCRIPTION    "This shows the maximum current of partition8."
    ::= { partition8BasicInfo 2 }

partition8MaxPower    OBJECT-TYPE
    SYNTAX    Integer32
    UNITS    "W"
    MAX-ACCESS    read-only
    STATUS    current
    DESCRIPTION    "This shows the maximum power of partition8."
    ::= { partition8BasicInfo 3 }

partition8ProcCoreCount    OBJECT-TYPE
    SYNTAX    Integer32
    MAX-ACCESS    read-only
    STATUS    current
    DESCRIPTION    "This shows the total number of CPU core of partition8."
    ::= { partition8BasicInfo 4 }

partition8DIMMCapacity    OBJECT-TYPE
    SYNTAX    Integer32
    UNITS    "GB"
    MAX-ACCESS    read-only
    STATUS    current
    DESCRIPTION    "This shows the total amount of DIMM capacity of partition8."
    ::= { partition8BasicInfo 5 }

partition8HVMLicenceModel    OBJECT-TYPE
    SYNTAX    DisplayString (SIZE(0..40))
    MAX-ACCESS    read-only
    STATUS    current
    DESCRIPTION    "This shows the HVM licence information of partition8 (model)."
    ::= { partition8BasicInfo 6 }

partition8HVMLicenceAvailableVersion    OBJECT-TYPE
    SYNTAX    DisplayString (SIZE(0..40))
    MAX-ACCESS    read-only
    STATUS    current
    DESCRIPTION    "This shows the HVM licence information of partition8 (available version)."
    ::= { partition8BasicInfo 7 }

partition8BladeConfig    OBJECT IDENTIFIER ::= { partition8BasicInfo 20 } 

partition8BladePrimarySlotNum    OBJECT-TYPE
    SYNTAX    Integer32
    MAX-ACCESS    read-only
    STATUS    current
    DESCRIPTION    "This shows the primary blade location of partition8."
    ::= { partition8BladeConfig 1 }

partition8BladeCount    OBJECT-TYPE
    SYNTAX    Integer32
    MAX-ACCESS    read-only
    STATUS    current
    DESCRIPTION    "This shows the number of blades that belong to the partition8."
    ::= { partition8BladeConfig 2 }

partition8BladeTable    OBJECT-TYPE
    SYNTAX SEQUENCE OF partition8BladeEntry
    MAX-ACCESS not-accessible
    STATUS     current
    DESCRIPTION "This shows the table of blade information of partition8."
    ::= { partition8BladeConfig 3 }

partition8BladeEntry    OBJECT-TYPE
    SYNTAX Partition8BladeEntry
    MAX-ACCESS not-accessible
    STATUS    current
    DESCRIPTION "This shows the entry of blade information of partition8."
    INDEX { partition8BladeIndex }
    ::= { partition8BladeTable 1 }

partition8BladeIndex    OBJECT-TYPE
    SYNTAX    Integer32
    MAX-ACCESS    read-only
    STATUS    current
    DESCRIPTION    "This shows the index of blade information of partition8."
    ::= { partition8BladeEntry 1 }

partition8BladeSlotNum    OBJECT-TYPE
    SYNTAX    Integer32
    MAX-ACCESS    read-only
    STATUS    current
    DESCRIPTION    "This shows the location of blade of partition8."
    ::= { partition8BladeEntry 2 }

partition8BladeObjectID    OBJECT-TYPE
    SYNTAX    OBJECT IDENTIFIER
    MAX-ACCESS    read-only
    STATUS    current
    DESCRIPTION    "This shows the Object ID of blade of partition8."
    ::= { partition8BladeEntry 3 }

Partition8BladeEntry ::= SEQUENCE {
    partition8BladeIndex
        Integer32,
    partition8BladeSlotNum
        Integer32,
    partition8BladeObjectID
        OBJECT IDENTIFIER
}

partition8Settings    OBJECT IDENTIFIER ::= { partition8 3 } 

partition8SettingsSystemMode    OBJECT-TYPE
    SYNTAX    INTEGER {
    basic(1), hvm(2), unknown(3)
    }
    MAX-ACCESS    read-only
    STATUS    current
    DESCRIPTION    "This shows the hvm mode setting of partition8."
    ::= { partition8Settings 1 }

partition8SettingsDIMMRedundancy    OBJECT-TYPE
    SYNTAX    INTEGER {
    redundancy(1), non-redundancy(2),unknown(3)
    }
    MAX-ACCESS    read-only
    STATUS    current
    DESCRIPTION    "This shows the DIMM redundancy of partition8."
    ::= { partition8Settings 2 }

partition8SettingsPreConfig    OBJECT-TYPE
    SYNTAX    INTEGER {
    enable(1), disable(2), unknown(3)
    }
    MAX-ACCESS    read-only
    STATUS    current
    DESCRIPTION    "This shows the validity of pre-configure setting of partition8."
    ::= { partition8Settings 3 }

partition8State    OBJECT IDENTIFIER ::= { partition8 4 } 

partition8StatePower    OBJECT-TYPE
    SYNTAX    INTEGER {
    poweroff (1), standby (2), poweron (3), unknown (4),poweron-executing (5),poweroff-executing (6)
    }
    MAX-ACCESS    read-only
    STATUS    current
    DESCRIPTION    "This shows the power supply state of partition8."
    ::= { partition8State 1 }

partition8StateHealth    OBJECT-TYPE
    SYNTAX    INTEGER {
    normal (1),fail (2),unknown (3)
    }
    MAX-ACCESS    read-only
    STATUS    current
    DESCRIPTION    "This shows the health state of partition8."
    ::= { partition8State 2 }

partition8StateSystemMode    OBJECT-TYPE
    SYNTAX    INTEGER {
    basic(1), hvm(2), unknown(3)
    }
    MAX-ACCESS    read-only
    STATUS    current
    DESCRIPTION    "This shows the hvm mode of partition8."
    ::= { partition8State 3 }

partition8StateConsumptionCurrent    OBJECT-TYPE
    SYNTAX    Integer32
    UNITS    "0.1 A"
    MAX-ACCESS    read-only
    STATUS    current
    DESCRIPTION    "This shows the consumption current of partition8."
    ::= { partition8State 4 }

partition8StatePowerConsumption    OBJECT-TYPE
    SYNTAX    Integer32
    UNITS    "W"
    MAX-ACCESS    read-only
    STATUS    current
    DESCRIPTION    "This shows the current power consumption of partition8."
    ::= { partition8State 5 }

partition8StatePreConfig    OBJECT-TYPE
    SYNTAX    INTEGER {
    not-get(1), not-set(2), getting(3), valid(4)
    }
    MAX-ACCESS    read-only
    STATUS    current
    DESCRIPTION    "This shows the run state of pre-configure of partition8."
    ::= { partition8State 6 }

-------------------------------------------------------------------------------
--*********
-- notification definitions
--*********

--------------------------------------------------------------------------------
--	alertTrap
--------------------------------------------------------------------------------

alertTrap
	OBJECT IDENTIFIER
	::=	{ compute 10 }

alertTrapCommon
	OBJECT IDENTIFIER
	::=	{ alertTrap 0 }

alertTrapInfLocalTime
	OBJECT-TYPE
	SYNTAX			DisplayString	(SIZE(0..28))
	MAX-ACCESS		read-only
	STATUS			current
	DESCRIPTION
		"VarBind01:LocalTime YYYY-MM-DD hh:mm:ss(+TZ)"
	::=	{ alertTrapCommon 1 }

alertTrapInfChassisID
	OBJECT-TYPE
	SYNTAX			DisplayString	(SIZE(0..16))
	MAX-ACCESS		read-only
	STATUS			current
	DESCRIPTION
		"VarBind02:ChassisID"
	::=	{ alertTrapCommon 2 }

alertTrapInfAlertLevel
	OBJECT-TYPE
	SYNTAX
		INTEGER
		{
			information	(1),
			warning		(2),
			error		(3),
			event		(4)
		}
	MAX-ACCESS		read-only
	STATUS			current
	DESCRIPTION		
		"VarBind03:AlertLevel
		1 = Information
		2 = Warning
		3 = Error
		4 = Event"
	::=	{ alertTrapCommon 3 }

alertTrapInfAlertID
	OBJECT-TYPE
	SYNTAX			DisplayString	(SIZE(0..4))
	MAX-ACCESS		read-only
	STATUS			current
	DESCRIPTION
		"VarBind04:AlertID"
	::=	{ alertTrapCommon 4 }

alertTrapInfAlertMessage
	OBJECT-TYPE
	SYNTAX			DisplayString	(SIZE(0..255))
	MAX-ACCESS		read-only
	STATUS			current
	DESCRIPTION
		"VarBind05:AlertMessage"
	::=	{ alertTrapCommon 5 }

alertTrapInfAlertOutbreakPart
	OBJECT-TYPE
	SYNTAX			DisplayString	(SIZE(0..2))
	MAX-ACCESS		read-only
	STATUS			current
	DESCRIPTION
		"VarBind06:AlertOutbreakPart
		00 = ServerModule
		01 = HDD Module
		02 = DVD Module
		03 = IOA
		04 = SVP Module
		05 = Power Supply Module
		06 = FAN Module
		07 = PCI Card
		08 = Partition
		09 = SW FAN Module
		10 = LAN SW Module
		11 = FC SW Module
		12 = Connector PK Module
		13 = Path Through SW Module
		14 = SAS SW Module
		15 = IOSW Module
		17 = I/O Board Module
		XX = Unknown"
	::=	{ alertTrapCommon 6 }

alertTrapInfAlertModuleType
	OBJECT-TYPE
	SYNTAX			DisplayString
	MAX-ACCESS		read-only
	STATUS			current
	DESCRIPTION
		"VarBind07:AlertModuleType"
	::=	{ alertTrapCommon 7 }

alertTrapInfAlertModuleLocation
	OBJECT-TYPE
	SYNTAX			DisplayString
	MAX-ACCESS		read-only
	STATUS			current
	DESCRIPTION
		"VarBind08:AlertModuleLocation"
	::=	{ alertTrapCommon 8 }

alertTrapInfAlertModuleModelName
	OBJECT-TYPE
	SYNTAX			DisplayString
	MAX-ACCESS		read-only
	STATUS			current
	DESCRIPTION
		"VarBind09:AlertModuleModelName"
	::=	{ alertTrapCommon 9 }

alertTrapInfAlertModuleSerialNum
	OBJECT-TYPE
	SYNTAX			DisplayString
	MAX-ACCESS		read-only
	STATUS			current
	DESCRIPTION
		"VarBind10:AlertModuleSerialNum"
	::=	{ alertTrapCommon 10 }

alertTrapInfAlertEventCode
	OBJECT-TYPE
	SYNTAX			DisplayString
	MAX-ACCESS		read-only
	STATUS			current
	DESCRIPTION
		"VarBind11:AlertEventCode"
	::=	{ alertTrapCommon 11 }

-------------------------------------------------------------------------------
-- BSX MIB
--------------------------------------------------------------------------------

bsm
	OBJECT IDENTIFIER
	::=	{ alertTrap 1 }

bsmAlertTrap
	OBJECT IDENTIFIER
	::=	{ bsm 1 }

--------------------------------------------------------------------------------

bsmAlertTrapSvp
	OBJECT IDENTIFIER
	::=	{ bsmAlertTrap 1 }

bsmAlertTrapSvpNon-Recoverable
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event of the fault level."
	::= { bsmAlertTrapSvp 1 }

bsmAlertTrapSvpSerious
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event of the warning level."
	::= { bsmAlertTrapSvp 2 }

bsmAlertTrapSvpInformation
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event of the information level."
	::= { bsmAlertTrapSvp 3 }

bsmAlertTrapSvpEvent
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event."
	::= { bsmAlertTrapSvp 4 }

--------------------------------------------------------------------------------

bsmAlertTrapBlade
	OBJECT IDENTIFIER
	::=	{ bsmAlertTrap 2 }

bsmAlertTrapBladeNon-Recoverable
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event of the fault level."
	::= { bsmAlertTrapBlade 1 }

bsmAlertTrapBladeSerious
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event of the warning level."
	::= { bsmAlertTrapBlade 2 }

bsmAlertTrapBladeInformation
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event of the information level."
	::= { bsmAlertTrapBlade 3 }

bsmAlertTrapBladeEvent
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event."
	::= { bsmAlertTrapBlade 4 }

--------------------------------------------------------------------------------

bsmAlertTrapOther
	OBJECT IDENTIFIER
	::=	{ bsmAlertTrap 20 }

bsmAlertTrapOtherNon-Recoverable
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event of the fault level."
	::= { bsmAlertTrapOther 1 }

bsmAlertTrapOtherSerious
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event of the warning level."
	::= { bsmAlertTrapOther 2 }

bsmAlertTrapOtherInformation
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event of the information level."
	::= { bsmAlertTrapOther 3 }

bsmAlertTrapOtherEvent
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event."
	::= { bsmAlertTrapOther 4 }

--------------------------------------------------------------------------------

bsmMIBGroups
	OBJECT IDENTIFIER
	::=	{ bsm 100 }

bsmAlertTrapInfoGroup
	OBJECT-GROUP
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"bsmAlertTrapInfoGroup"
	::= { bsmMIBGroups 1 }

bsmAlertTrapGroup
	NOTIFICATION-GROUP
	NOTIFICATIONS
	{
		bsmAlertTrapSvpNon-Recoverable ,
		bsmAlertTrapSvpSerious ,
		bsmAlertTrapSvpInformation ,
		bsmAlertTrapSvpEvent ,

		bsmAlertTrapBladeNon-Recoverable ,
		bsmAlertTrapBladeSerious ,
		bsmAlertTrapBladeInformation ,
		bsmAlertTrapBladeEvent ,

		bsmAlertTrapOtherNon-Recoverable ,
		bsmAlertTrapOtherSerious ,
		bsmAlertTrapOtherInformation ,
		bsmAlertTrapOtherEvent
	}
	STATUS			current
	DESCRIPTION		"bsmAlertTrapGroup"
	::= { bsmMIBGroups 2 }

--------------------------------------------------------------------------------

hcsm
	OBJECT IDENTIFIER
	::=	{ alertTrap 2 }

hcsmAlertTrap
	OBJECT IDENTIFIER
	::=	{ hcsm 1 }

--------------------------------------------------------------------------------

hcsmAlertTrapMonitoring
	OBJECT IDENTIFIER
	::=	{ hcsmAlertTrap 1 }

hcsmAlertTrapMonitoringError
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the fault level was encountered as monitoring alert."
	::= { hcsmAlertTrapMonitoring 1 }

hcsmAlertTrapMonitoringWarning
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the warning level was encountered as monitoring alert."
	::= { hcsmAlertTrapMonitoring 2 }

hcsmAlertTrapMonitoringInformation
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the information level was encountered as monitoring alert."
	::= { hcsmAlertTrapMonitoring 3 }

--------------------------------------------------------------------------------

hcsmAlertTrapEvent
	OBJECT IDENTIFIER
	::=	{ hcsmAlertTrap 2 }

hcsmAlertTrapEventError
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the fault level was encountered as event alert."
	::= { hcsmAlertTrapEvent 1 }

hcsmAlertTrapEventWarning
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the warning level was encountered as event alert."
	::= { hcsmAlertTrapEvent 2 }

hcsmAlertTrapEventInformation
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the information level was encountered as event alert."
	::= { hcsmAlertTrapEvent 3 }

--------------------------------------------------------------------------------

hcsmAlertTrapStatusChange
	OBJECT IDENTIFIER
	::=	{ hcsmAlertTrap 3 }

hcsmAlertTrapStatusChangeError
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the fault level was encountered as state change alert."
	::= { hcsmAlertTrapStatusChange 1 }

hcsmAlertTrapStatusChangeWarning
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the warning level was encountered as state change alert."
	::= { hcsmAlertTrapStatusChange 2 }

hcsmAlertTrapStatusChangeInformation
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the information level was encountered as state change alert."
	::= { hcsmAlertTrapStatusChange 3 }

--------------------------------------------------------------------------------

hcsmMIBGroups
	OBJECT IDENTIFIER
	::=	{ hcsm 100 }

hcsmAlertTrapInfoGroup
	OBJECT-GROUP
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"hcsmAlertTrapInfoGroup"
	::= { hcsmMIBGroups 1 }

hcsmAlertTrapGroup
	NOTIFICATION-GROUP
	NOTIFICATIONS
	{
		hcsmAlertTrapMonitoringError ,
		hcsmAlertTrapMonitoringWarning ,
		hcsmAlertTrapMonitoringInformation ,

		hcsmAlertTrapEventError ,
		hcsmAlertTrapEventWarning ,
		hcsmAlertTrapEventInformation ,

		hcsmAlertTrapStatusChangeError ,
		hcsmAlertTrapStatusChangeWarning ,
		hcsmAlertTrapStatusChangeInformation
	}
	STATUS			current
	DESCRIPTION		"hcsmAlertTrapGroup"
	::= { hcsmMIBGroups 2 }


-------------------------------------------------------------------------------

END
